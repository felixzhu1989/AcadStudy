Attribute VB_Name = "模块1"
Option Explicit
'创建单行文字
Public Sub demoText()
    Dim pt As Variant
    Dim text As String
    Dim height As Double
    
    pt = ThisDrawing.Utility.GetPoint(, "拾取文字的插入点:")
    text = "AutoCAD  VBA 二次开发"
    height = 3
    
    Dim objText As AcadText
    Set objText = ThisDrawing.ModelSpace.AddText(text, pt, height)
    'objText.Rotation = 15 * 3.1415926 / 180
    'objText.height = 4
    'objText.Backward = True
    'objText.UpsideDown = True
    objText.Alignment = acAlignmentBottomCenter
    objText.Move objText.InsertionPoint, pt
    
    Stop
    
End Sub
'创建多行文字
Public Sub demoMText()
     Dim pt As Variant
    Dim text As String
    Dim width As Double
    pt = ThisDrawing.Utility.GetPoint(, "拾取文字的插入点:")
    text = "AutoCAD  VBA 二次开发"
    width = 50
    Dim objMText As AcadMText
    Set objMText = ThisDrawing.ModelSpace.AddMText(pt, width, text)
    objMText.height = 2.5
    
    Stop
End Sub
