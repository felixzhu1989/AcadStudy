Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit

Private Sub AcadDocument_BeginSave(ByVal FileName As String)

End Sub

Attribute VB_Name = "模块1"
Option Explicit
Public Sub drawLine()
    Dim pt1(0 To 2) As Double
    Dim pt2(0 To 2) As Double
    
    pt1(0) = 0
    pt1(1) = 0
    pt1(2) = 0
    pt2(0) = 100: pt2(1) = 100: pt2(2) = 0
    
    ThisDrawing.ModelSpace.AddLine pt1, pt2
End Sub

Public Sub demo()
 Dim pt1(0 To 2) As Double
'    Dim pt2(0 To 2) As Double
'
    pt1(0) = 300
    pt1(1) = 100
    pt1(2) = 0
'    pt2(0) = 100: pt2(1) = 100: pt2(2) = 0
'
'    Dim objLine As AcadLine
'    Set objLine = AddLine(pt1, pt2)
'    objLine.color = acRed
'    objLine.Lineweight = acLnWt050
    Dim x1 As Double
    Dim x2 As Double
    Dim y1 As Double
    Dim y2 As Double
    x1 = 10: y1 = 10
    x2 = 200: y2 = 200
    Dim objLine As AcadLine
'    Set objLine = AddlineXY(x1, y1, x2, y2)
    'Set objLine = AddLineReXY(pt1, x2, y2)
    Dim angle As Double
    Dim distance As Double
    angle = 3.1415926 / 2
    distance = 100
    Set objLine = AddLineReAL(pt1, angle, distance)
End Sub

Attribute VB_Name = "模块2"
Option Explicit
'根据起点和终点创建直线
Public Function AddLine(ByVal ptStart As Variant, ByVal ptEnd As Variant) As AcadLine
    Set AddLine = ThisDrawing.ModelSpace.AddLine(ptStart, ptEnd)
End Function
'根据起点和终点的坐标创建直线
Public Function AddlineXY(ByVal x1 As Double, ByVal y1 As Double, ByVal x2 As Double, ByVal y2 As Double) As AcadLine
    Dim pt1(2) As Double
    Dim pt2(2) As Double
    
    pt1(0) = x1: pt1(1) = y1: pt1(2) = 0 '注意不要忘记给数组的最后一个变量赋值
    pt2(0) = x2: pt2(1) = y2: pt2(2) = 0
    Set AddlineXY = ThisDrawing.ModelSpace.AddLine(pt1, pt2)
End Function

'根据起点和相对起点的直角坐标创建直线
Public Function AddLineReXY(ByVal ptSt As Variant, ByVal x As Double, ByVal y As Double) As AcadLine
    Dim ptEn(2) As Double
    ptEn(0) = ptSt(0) + x: ptEn(1) = ptSt(1) + y: ptEn(2) = 0
    Set AddLineReXY = ThisDrawing.ModelSpace.AddLine(ptSt, ptEn)
End Function
'根据起点和相对极坐标创建直线
Public Function AddLineReAL(ByVal ptSt As Variant, ByVal angle As Double, ByVal dist As Double) As AcadLine
    Dim ptEn(2) As Double
    ptEn(0) = ptSt(0) + dist * Cos(angle)
    ptEn(1) = ptSt(1) + dist * Sin(angle)
    ptEn(2) = ptSt(2)
    Set AddLineReAL = ThisDrawing.ModelSpace.AddLine(ptSt, ptEn)
End Function
