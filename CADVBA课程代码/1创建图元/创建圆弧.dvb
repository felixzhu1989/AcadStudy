Attribute VB_Name = "模块1"
Option Explicit
Public Const PI As Double = 3.1415926

'创建圆弧
Public Sub createArc()
    Dim center(2) As Double
    Dim radius As Double
    Dim startAngle As Double
    Dim endAngle As Double
    
    center(0) = 100: center(1) = 100: center(2) = 0
    radius = 50
    startAngle = PI / 4
    endAngle = 15 * PI / 4
    
    Dim objArc As AcadArc
    Set objArc = ThisDrawing.ModelSpace.AddArc(center, radius, startAngle, endAngle)
End Sub
'测试
Public Sub demoArc1()
    Dim ptCen As Variant
    Dim ptS As Variant
    Dim ptN As Variant
    ptCen = ThisDrawing.Utility.GetPoint(, "圆心：")
    ptS = ThisDrawing.Utility.GetPoint(ptCen, "起点：")
    ptN = ThisDrawing.Utility.GetPoint(ptCen, "端点：")
    
    Dim objArc As AcadArc
    Set objArc = AddArcCSN(ptCen, ptS, ptN)
End Sub
Public Sub demoArc2()
    Dim ptCen As Variant
    Dim ptS As Variant
    Dim angle As Double
    
    ptCen = ThisDrawing.Utility.GetPoint(, "圆心：")
    ptS = ThisDrawing.Utility.GetPoint(ptCen, "起点：")
    'angle = ThisDrawing.Utility.GetReal("圆弧角度：")
    angle = ThisDrawing.Utility.GetReal("圆弧角度(角度值）:")
    angle = angle * PI / 180
    Dim objArc As AcadArc
    Set objArc = AddArcCSA(ptCen, ptS, angle)
End Sub
Public Sub demoArc3()
    Dim ptCen As Variant
    Dim ptS As Variant
    Dim chordLength As Double
    
    
    ptCen = ThisDrawing.Utility.GetPoint(, "圆心：")
    ptS = ThisDrawing.Utility.GetPoint(ptCen, "起点：")
    chordLength = ThisDrawing.Utility.GetReal("玄长:")
    Dim objArc As AcadArc
    Set objArc = AddArcCSC(ptCen, ptS, chordLength)
End Sub
Public Sub demoArc4()
    Dim ptCen As Variant
    Dim ptS As Variant
    Dim arcLength As Double
    
    
    ptCen = ThisDrawing.Utility.GetPoint(, "圆心：")
    ptS = ThisDrawing.Utility.GetPoint(ptCen, "起点：")
    arcLength = ThisDrawing.Utility.GetReal("弧长:")
    Dim objArc As AcadArc
    Set objArc = AddArcCSAL(ptCen, ptS, arcLength)
End Sub
Public Sub demoArc5()
    Dim pt1 As Variant
    Dim pt2 As Variant
    Dim pt3 As Variant
    
    pt1 = ThisDrawing.Utility.GetPoint(, "第1个点")
    pt2 = ThisDrawing.Utility.GetPoint(, "第2个点")
    pt3 = ThisDrawing.Utility.GetPoint(, "第3个点")
    Dim objArc As AcadArc
    Set objArc = AddArc3P(pt1, pt2, pt3)
End Sub

Attribute VB_Name = "模块2"
Option Explicit

'通过圆心,半径,起始角度和终止角度创建圆弧
Public Function AddArc(ByVal ptCen As Variant, ByVal radius As Double, ByVal stAng As Double, ByVal enAng As Double) As AcadArc
    Set AddArc = ThisDrawing.ModelSpace.AddArc(ptCen, radius, stAng, enAng)
End Function
'通过圆心、起点、端点创建圆弧
Public Function AddArcCSN(ByVal ptCen As Variant, ByVal ptS As Variant, ByVal ptN As Variant) As AcadArc
    Dim radius As Double
    Dim startAngle As Double
    Dim endAngle As Double
    
    radius = Sqr((ptCen(0) - ptS(0)) ^ 2 + (ptCen(1) - ptS(1)) ^ 2 + (ptCen(2) - ptS(2)) ^ 2)
    startAngle = ThisDrawing.Utility.AngleFromXAxis(ptCen, ptS)
    endAngle = ThisDrawing.Utility.AngleFromXAxis(ptCen, ptN)
    Set AddArcCSN = ThisDrawing.ModelSpace.AddArc(ptCen, radius, startAngle, endAngle)
End Function
'通过圆心,起点和圆弧的角度创建圆弧
Public Function AddArcCSA(ByVal ptCen As Variant, ByVal ptSt As Variant, ByVal angle As Double) As AcadArc
    Dim radius As Double
    Dim stAng As Double
    Dim enAng As Double
    
    radius = Sqr((ptSt(0) - ptCen(0)) ^ 2 + (ptSt(1) - ptCen(1)) ^ 2)
    stAng = ThisDrawing.Utility.AngleFromXAxis(ptCen, ptSt)
    enAng = stAng + angle
    Set AddArcCSA = ThisDrawing.ModelSpace.AddArc(ptCen, radius, stAng, enAng)
End Function
'圆心、起点、玄长
Public Function AddArcCSC(ByVal ptCen As Variant, ByVal ptS As Variant, ByVal chordLength As Double) As AcadArc
    Dim radius As Double
    Dim startAngle As Double
    Dim endAngle As Double
    
    radius = Sqr((ptS(0) - ptCen(0)) ^ 2 + (ptS(1) - ptCen(1)) ^ 2)
    startAngle = ThisDrawing.Utility.AngleFromXAxis(ptCen, ptS)
    endAngle = startAngle + 2 * Atn((chordLength / radius / 2) / Sqr(1 - (chordLength / radius / 2) ^ 2))
    Set AddArcCSC = ThisDrawing.ModelSpace.AddArc(ptCen, radius, startAngle, endAngle)
End Function
'通过圆心,起点和弧长来创建圆
Public Function AddArcCSAL(ByVal ptCen As Variant, ByVal ptSt As Variant, ByVal arcLength As Double) As AcadArc
    Dim radius As Double
    Dim stAng As Double
    Dim enAng As Double
    radius = Sqr((ptSt(0) - ptCen(0)) ^ 2 + (ptSt(1) - ptCen(1)) ^ 2)
    stAng = ThisDrawing.Utility.AngleFromXAxis(ptCen, ptSt)
    enAng = stAng + arcLength / radius
    Set AddArcCSAL = ThisDrawing.ModelSpace.AddArc(ptCen, radius, stAng, enAng)
End Function
'通过三点来创建圆弧,这三个点在圆弧上
Public Function AddArc3P(ByVal pt1 As Variant, ByVal pt2 As Variant, ByVal pt3 As Variant) As AcadArc
    Dim ptCen As Variant
    Dim radius As Double
    Dim stAng As Double
    Dim enAng As Double
    '三点求圆心
    Dim pt12(2) As Double
    Dim pt23(2) As Double
    pt12(0) = (pt1(0) + pt2(0)) / 2
    pt12(1) = (pt1(1) + pt2(1)) / 2
    pt12(2) = (pt1(2) + pt2(2)) / 2
    pt23(0) = (pt2(0) + pt3(0)) / 2
    pt23(1) = (pt2(1) + pt3(1)) / 2
    pt23(2) = (pt2(2) + pt3(2)) / 2
    Dim angle1 As Double
    Dim angle2 As Double
    angle1 = ThisDrawing.Utility.AngleFromXAxis(pt1, pt2) + PI / 2
    angle2 = ThisDrawing.Utility.AngleFromXAxis(pt2, pt3) + PI / 2
    Dim line12z As AcadLine
    Dim line23z As AcadLine
    Set line12z = AddLineReAL(pt12, angle1, 100)
    Set line23z = AddLineReAL(pt23, angle2, 100)
    ptCen = line12z.IntersectWith(line23z, acExtendBoth)
    line12z.Delete: line23z.Delete
    
    radius = Sqr((pt1(0) - ptCen(0)) ^ 2 + (pt1(1) - ptCen(1)) ^ 2)
    stAng = ThisDrawing.Utility.AngleFromXAxis(ptCen, pt1)
    enAng = ThisDrawing.Utility.AngleFromXAxis(ptCen, pt3)
    Set AddArc3P = ThisDrawing.ModelSpace.AddArc(ptCen, radius, stAng, enAng)
End Function


'通过起点和极坐标创建直线
Public Function AddLineReAL(ByVal ptSt As Variant, ByVal angle As Double, ByVal dist As Double) As AcadLine
    Dim ptEn(2) As Double
    ptEn(0) = ptSt(0) + dist * Cos(angle)
    ptEn(1) = ptSt(1) + dist * Sin(angle)
    ptEn(2) = ptSt(2)
    Set AddLineReAL = ThisDrawing.ModelSpace.AddLine(ptSt, ptEn)
End Function
