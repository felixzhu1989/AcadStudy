Attribute VB_Name = "模块1"
Public Sub showEnity()
    Dim objEntity As AcadEntity
    Dim picked
    ThisDrawing.Utility.GetEntity objEntity, picked
    objEntity.color = acBlue
End Sub
Public Sub createHatch()
    Dim pt1 As Variant
    Dim pt2 As Variant
    pt1 = ThisDrawing.Utility.GetPoint(, "左下角:")
    pt2 = ThisDrawing.Utility.GetCorner(pt1, "右上角:")
    
    Dim objRec(0) As AcadLWPolyline
    Set objRec(0) = AddRectAng(pt1, pt2)
    Dim patternName As String
    
    patternName = "ANSI33"
    Dim objHatch As AcadHatch
    Set objHatch = ThisDrawing.ModelSpace.addHatch(0, patternName, True)
    objHatch.AppendInnerLoop (objRec)
    'objHatch.PatternAngle = 30
    objHatch.PatternScale = 20
    objHatch.color = acRed
End Sub
Public Sub demoHatch1()
    Dim pt As Variant
    Dim radius As Double
    Dim objEntity(0) As AcadEntity
    pt = ThisDrawing.Utility.GetPoint(, "圆心:")
    radius = ThisDrawing.Utility.GetDistance(pt, "半径:")
    Set objEntity(0) = ThisDrawing.ModelSpace.AddCircle(pt, radius)
    Dim patternName As String
    patternName = "ANSI31"
    
    Dim objHatch As AcadHatch
    Set objHatch = addHatch(objEntity, patternName)
End Sub
'图案填充
Public Function addHatch(ByRef entity() As AcadEntity, ByVal patternName As String) As AcadHatch
    Dim objHatch As AcadHatch
    Set objHatch = ThisDrawing.ModelSpace.addHatch(0, patternName, True)
    objHatch.AppendInnerLoop (entity)
    'objHatch.PatternAngle = 30
    objHatch.PatternScale = 20
    objHatch.color = acRed
    Set addHatch = objHatch
End Function
'通过多段线创建矩形,并进行封装
Public Function AddRectAng(ByVal pt1 As Variant, ByVal pt2 As Variant) As AcadLWPolyline
   
    Dim ptArr(7) As Double
    Dim objRec As AcadLWPolyline
    
    ptArr(0) = pt1(0): ptArr(1) = pt1(1)
    ptArr(2) = pt2(0): ptArr(3) = pt1(1)
    ptArr(4) = pt2(0): ptArr(5) = pt2(1)
    ptArr(6) = pt1(0): ptArr(7) = pt2(1)
    
    Set objRec = ThisDrawing.ModelSpace.AddLightWeightPolyline(ptArr)
    objRec.Closed = True
    Set AddRectAng = objRec
End Function
'封装渐变填充
Public Function AddHatchC(ByRef objList() As AcadEntity, ByVal patternType As Long, ByVal patternName As String, ByVal color1 As AcadAcCmColor, ByVal color2 As AcadAcCmColor) As AcadHatch
    Dim objHatch As AcadHatch
    Set objHatch = ThisDrawing.ModelSpace.addHatch(patternType, patternName, True, 1)
    objHatch.GradientColor1 = color1
    objHatch.GradientColor2 = color2
    objHatch.AppendOuterLoop (objList)
    objHatch.Evaluate
    ThisDrawing.Regen True
    Set AddHatchC = objHatch
End Function
Public Sub demoAddHatchC()
    Dim objList(0) As AcadEntity
    Dim patternType As Long
    Dim patternName As String
    Dim objHatch As AcadHatch
    
    patternType = 0
    patternName = "LINEAR"
    
    Dim color1 As New AcadAcCmColor
    Dim color2 As New AcadAcCmColor
    color1.ColorIndex = 1
    color2.ColorIndex = 2
    Dim pt1 As Variant
    Dim pt2 As Variant
    pt1 = ThisDrawing.Utility.GetPoint(, "请指定矩形第一个角点:")
    pt2 = ThisDrawing.Utility.GetCorner(pt1, "指定矩形的第二个角点:")
    Set objList(0) = AddRectAng(pt1, pt2)
    
    Set objHatch = AddHatchC(objList, patternType, patternName, color1, color2)
End Sub
