Attribute VB_Name = "模块1"
Option Explicit

Public Sub showEntity()
    Dim objEntity As AcadEntity
    Dim ptPicked As Variant
    
    ThisDrawing.Utility.GetEntity objEntity, ptPicked
    Stop
End Sub
'测试矩形
Public Sub demoRec()
    Dim pt1 As Variant
    Dim pt2 As Variant
    
    pt1 = ThisDrawing.Utility.GetPoint(, "拾取第一个点:")
    pt2 = ThisDrawing.Utility.GetCorner(pt1, "拾取对角点:")
    
    Dim objRec As AcadLWPolyline
    Set objRec = AddRec(pt1, pt2)
    
End Sub

'测试多边形
Public Sub demoPolygon()
    Dim ptCen As Variant
    Dim pt As Variant
    Dim side As Integer
    
    ptCen = ThisDrawing.Utility.GetPoint(, "多边形的中心:")
    pt = ThisDrawing.Utility.GetPoint(ptCen, "多边形的一个顶点 :")
    side = ThisDrawing.Utility.GetInteger("多边形的边数：")
    Dim objPolygon As AcadLWPolyline
    'Set objPolygon = AddPolygonInside(ptCen, pt, side)
    Set objPolygon = AddPolygonOutside(ptCen, pt, side)
End Sub

Attribute VB_Name = "模块2"
Option Explicit
Public Const PI As Double = 3.1415926
'创建矩形
Public Function AddRec(ByVal pt1 As Variant, ByVal pt2 As Variant) As AcadLWPolyline
    Dim ptArr(7) As Double
    ptArr(0) = pt1(0): ptArr(1) = pt1(1)
    ptArr(2) = pt2(0): ptArr(3) = pt1(1)
    ptArr(4) = pt2(0): ptArr(5) = pt2(1)
    ptArr(6) = pt1(0): ptArr(7) = pt2(1)
    
    Set AddRec = ThisDrawing.ModelSpace.AddLightWeightPolyline(ptArr)
    AddRec.Closed = True
End Function
'多边形,内接于圆
Public Function AddPolygonInside(ByVal ptCen As Variant, ByVal pt As Variant, ByVal side As Integer) As AcadLWPolyline
    Dim ptArr() As Double
    ReDim ptArr(side * 2 - 1) As Double
    Dim radius As Double
    Dim angleFromX As Double
    Dim angleDiv As Double
    
    angleFromX = ThisDrawing.Utility.AngleFromXAxis(ptCen, pt)
    angleDiv = 2 * PI / side
    radius = Sqr((ptCen(0) - pt(0)) ^ 2 + (ptCen(1) - pt(1)) ^ 2)
    Dim i As Integer
    For i = 0 To side * 2 - 2 Step 2
        ptArr(i) = ptCen(0) + Cos(angleFromX) * radius
        ptArr(i + 1) = ptCen(1) + Sin(angleFromX) * radius
        angleFromX = angleFromX + angleDiv
    Next i
    
    Set AddPolygonInside = ThisDrawing.ModelSpace.AddLightWeightPolyline(ptArr)
    AddPolygonInside.Closed = True
End Function
'多边形,外切于圆
Public Function AddPolygonOutside(ByVal ptCen As Variant, ByVal pt As Variant, ByVal side As Integer) As AcadLWPolyline
    Dim ptArr() As Double
    ReDim ptArr(side * 2 - 1) As Double
    Dim radius As Double
    Dim angleFromX As Double
    Dim angleDiv As Double
    angleFromX = ThisDrawing.Utility.AngleFromXAxis(ptCen, pt)
    angleDiv = 2 * PI / side
    angleFromX = angleFromX + angleDiv / 2
    
    radius = Sqr((ptCen(0) - pt(0)) ^ 2 + (ptCen(1) - pt(1)) ^ 2)
    radius = radius / Cos(angleDiv / 2)
     Dim i As Integer
    For i = 0 To side * 2 - 2 Step 2
        ptArr(i) = ptCen(0) + Cos(angleFromX) * radius
        ptArr(i + 1) = ptCen(1) + Sin(angleFromX) * radius
        angleFromX = angleFromX + angleDiv
    Next i
    Set AddPolygonOutside = ThisDrawing.ModelSpace.AddLightWeightPolyline(ptArr)
    AddPolygonOutside.Closed = True
End Function
