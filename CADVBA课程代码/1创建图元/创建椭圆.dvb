Attribute VB_Name = "模块1"
Option Explicit
'创建椭圆
Public Sub createEllipse()
    Dim center As Variant
    Dim majorAxis As Variant
    Dim radiusRatio As Double
    
    center = ThisDrawing.Utility.GetPoint(, "拾取椭圆的中心:")
    majorAxis = ThisDrawing.Utility.GetPoint(center, "端点:")
    majorAxis(0) = majorAxis(0) - center(0): majorAxis(1) = majorAxis(1) - center(1): majorAxis(2) = majorAxis(2) - center(2):
    radiusRatio = ThisDrawing.Utility.GetReal("短长轴比率:")
    If radiusRatio > 1 Then
        radiusRatio = 1
    End If
    Dim objEllipse
    Set objEllipse = ThisDrawing.ModelSpace.AddEllipse(center, majorAxis, radiusRatio)
  
End Sub
