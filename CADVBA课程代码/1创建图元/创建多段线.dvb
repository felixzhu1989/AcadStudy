Attribute VB_Name = "模块1"
Option Explicit
'查看图元
Public Sub showEntity()
    Dim objEntity As AcadEntity
    Dim ptPicked As Variant
    ThisDrawing.Utility.GetEntity objEntity, ptPicked, "选择图元:"
    Stop
End Sub
'创建轻量多段线
Public Sub createLWPline()
    Dim pt(5) As Double
    pt(0) = 0: pt(1) = 0:
    pt(2) = 100: pt(3) = 0:
    pt(4) = 100: pt(5) = 100
    
    Dim objLWPline As AcadLWPolyline
    Set objLWPline = ThisDrawing.ModelSpace.AddLightWeightPolyline(pt)
    objLWPline.Closed = True
    objLWPline.ConstantWidth = 0.5
    Dim color As New AcadAcCmColor
    color.ColorIndex = 1
    objLWPline.TrueColor = color
End Sub
'创建多段线
Public Sub createPline()
    Dim pt(8) As Double
    pt(0) = 0: pt(1) = 0: pt(2) = 0
    pt(3) = 100: pt(4) = 0: pt(5) = 0
    pt(6) = 100: pt(7) = 100: pt(8) = 0
    Dim objPline As AcadPolyline
    Set objPline = ThisDrawing.ModelSpace.AddPolyline(pt)
    objPline.Closed = True
End Sub
