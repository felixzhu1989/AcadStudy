Attribute VB_Name = "模块1"
Option Explicit

'创建圆
Public Sub createCirlce()
    Dim ptCen(2) As Double
    Dim radius As Double
    
    Dim objCircle As AcadCircle
    
    ptCen(0) = 100: ptCen(1) = 100: ptCen(2) = 0
    radius = 50
    Set objCircle = ThisDrawing.ModelSpace.AddCircle(ptCen, radius)
End Sub
'圆心半径测试
Public Sub demoCircle1()
    Dim ptCen(2) As Double
    Dim radius As Double
    
    Dim objCircle As AcadCircle
    
    ptCen(0) = 100: ptCen(1) = 100: ptCen(2) = 0
    radius = 50
    Set objCircle = AddCircleCR(ptCen, radius)
End Sub
'两点测试
Public Sub demoCircle2()
    Dim pt1(2) As Double
    Dim pt2(2) As Double
    Dim objCircle As AcadCircle
    
    pt1(0) = 0: pt1(1) = 0: pt1(2) = 0
    pt2(0) = 200: pt2(1) = 200: pt2(2) = 0
    Set objCircle = AddCircle2P(pt1, pt2)
End Sub
'三点测试
Public Sub demoCircle3()
    Dim pt1 As Variant
    Dim pt2 As Variant
    Dim pt3 As Variant
    
    pt1 = ThisDrawing.Utility.GetPoint(, "第一点:")
    pt2 = ThisDrawing.Utility.GetPoint(pt1, "第二个点:")
    pt3 = ThisDrawing.Utility.GetPoint(pt2, "第三个点:")
    
    Dim objCircle As AcadCircle
    Set objCircle = AddCircle3P(pt1, pt2, pt3)
    
End Sub
'绘制同心圆
Public Sub aCircle()
    Dim pt(2) As Double
    Dim radius As Double
    pt(0) = 0: pt(1) = 0: pt(2) = 0
    radius = 50
    Dim i As Integer
    For i = 0 To 100
        ThisDrawing.ModelSpace.AddCircle pt, radius + i * 10
    Next i
End Sub

Public Sub test()
    Dim pt(2) As Double
    Dim radius As Double
    radius = 50
    Dim i As Integer
    Dim j As Integer
    For i = 0 To 10
        For j = 0 To 10
            pt(0) = i * 100: pt(1) = j * 100: pt(2) = 0
            ThisDrawing.ModelSpace.AddCircle pt, radius
        Next j
    Next i
End Sub

Attribute VB_Name = "模块2"
Option Explicit
Public Const PI As Double = 3.1415926
'通过圆心和半径创建圆
Public Function AddCircleCR(ByVal ptCen As Variant, ByVal radius As Double) As AcadCircle
    Set AddCircleCR = ThisDrawing.ModelSpace.AddCircle(ptCen, radius)
End Function

'通过圆心和直径创建圆

Public Function AddCircleCD(ByVal ptCen As Variant, ByVal diameter As Double) As AcadCircle
    Set AddCircleCD = ThisDrawing.ModelSpace.AddCircle(ptCen, diameter / 2)
End Function
'通过两点创建圆,两点为圆的直径上的两个点
Public Function AddCircle2P(ByVal pt1 As Variant, pt2 As Variant) As AcadCircle
    Dim ptCen(2) As Double
    Dim radius As Double
    ptCen(0) = (pt1(0) + pt2(0)) / 2
    ptCen(1) = (pt1(1) + pt2(1)) / 2
    ptCen(2) = (pt1(2) + pt2(2)) / 2
    radius = Sqr((pt1(0) - pt2(0)) ^ 2 + (pt1(1) - pt2(1)) ^ 2) / 2
    Set AddCircle2P = ThisDrawing.ModelSpace.AddCircle(ptCen, radius)
End Function

'通过三点创建圆
Public Function AddCircle3P(ByVal pt1 As Variant, ByVal pt2 As Variant, ByVal pt3 As Variant) As AcadCircle
    Dim ptCen As Variant
    Dim radius As Double
    '求出任意两条直线的中心点
    Dim pt12(2) As Double
    Dim pt23(2) As Double
    pt12(0) = (pt1(0) + pt2(0)) / 2
    pt12(1) = (pt1(1) + pt2(1)) / 2
    pt12(2) = (pt1(2) + pt2(2)) / 2
    pt23(0) = (pt3(0) + pt2(0)) / 2
    pt23(1) = (pt3(1) + pt2(1)) / 2
    pt23(2) = (pt3(2) + pt2(2)) / 2
    
    Dim line12 As AcadLine
    Dim line23 As AcadLine
    Dim line12z As AcadLine
    Dim line23z As AcadLine
    
    Set line12 = ThisDrawing.ModelSpace.AddLine(pt1, pt2)
    Set line23 = ThisDrawing.ModelSpace.AddLine(pt2, pt3)
    Dim angle12z As Double
    Dim angle23z As Double
    angle12z = line12.angle + PI / 2
    angle23z = line23.angle + PI / 2
    Set line12z = AddLineReAL(pt12, angle12z, 100)
    Set line23z = AddLineReAL(pt23, angle23z, 100)
    ptCen = line12z.IntersectWith(line23z, acExtendBoth)
    radius = Sqr((pt1(0) - ptCen(0)) ^ 2 + (pt1(1) - ptCen(1)) ^ 2)
    
    '删除模型空间的多余辅助线
    line12.Delete: line23.Delete: line12z.Delete: line23z.Delete
    
    Set AddCircle3P = ThisDrawing.ModelSpace.AddCircle(ptCen, radius)
End Function
'根据起点和相对极坐标创建直线
Public Function AddLineReAL(ByVal ptSt As Variant, ByVal angle As Double, ByVal dist As Double) As AcadLine
    Dim ptEn(2) As Double
    ptEn(0) = ptSt(0) + dist * Cos(angle)
    ptEn(1) = ptSt(1) + dist * Sin(angle)
    ptEn(2) = ptSt(2)
    Set AddLineReAL = ThisDrawing.ModelSpace.AddLine(ptSt, ptEn)
End Function
