Attribute VB_Name = "UserForm1"
Attribute VB_Base = "0{C7A13993-80A7-4FA6-80D8-1173F955DC85}{F27FF01D-B9BD-4085-B223-C0A5CB7FFE7D}"
Attribute VB_GlobalNameSpace = False
Attribute VB_Creatable = False
Attribute VB_PredeclaredId = True
Attribute VB_Exposed = False
Attribute VB_TemplateDerived = False
Attribute VB_Customizable = False
Option Explicit

Private Sub cmdOK_Click()
On Error Resume Next
    SSet.Delete
    dic.RemoveAll
    End
End Sub

Private Sub cmdPick_Click()
    UserForm1.Hide
    Call pickSSet
    Txt6dB.Text = dic("6dB") * ComboBox1.Text
    Txt10dB.Text = dic("10dB") * ComboBox1.Text
    Txt15dB.Text = dic("15dB") * ComboBox1.Text
    Txt20dB.Text = dic("20dB") * ComboBox1.Text
    Txt30dB.Text = dic("30dB") * ComboBox1.Text
    Txt40dB.Text = dic("40dB") * ComboBox1.Text
    Txt2gf.Text = dic("二功分") * ComboBox1.Text
    Txt3gf.Text = dic("三功分") * ComboBox1.Text
    Txt4gf.Text = dic("四功分") * ComboBox1.Text
    UserForm1.show
End Sub

Private Sub ComboBox1_Change()
    Txt6dB.Text = dic("6dB") * ComboBox1.Text
    Txt10dB.Text = dic("10dB") * ComboBox1.Text
    Txt15dB.Text = dic("15dB") * ComboBox1.Text
    Txt20dB.Text = dic("20dB") * ComboBox1.Text
    Txt30dB.Text = dic("30dB") * ComboBox1.Text
    Txt40dB.Text = dic("40dB") * ComboBox1.Text
    Txt2gf.Text = dic("二功分") * ComboBox1.Text
    Txt3gf.Text = dic("三功分") * ComboBox1.Text
    Txt4gf.Text = dic("四功分") * ComboBox1.Text
End Sub

Private Sub UserForm_Initialize()
    ComboBox1.AddItem 1
    ComboBox1.AddItem 2
    ComboBox1.Text = 1
    Set SSet = createSSet("tongji")
    Set dic = CreateObject("scripting.dictionary")
    dic.CompareMode = TextCompare
End Sub

Attribute VB_Name = "模块1"
Option Explicit
Public SSet As AcadSelectionSet
Public dic As New Dictionary

Public Sub pickSSet()
On Error Resume Next
    dic.RemoveAll
    Dim pt1 As Variant
    Dim pt2 As Variant
    pt1 = ThisDrawing.Utility.GetPoint(, "选择图元:")
    pt2 = ThisDrawing.Utility.GetCorner(pt1, "选择图元:")
    
    Dim fType(0) As Integer
    Dim fData(0) As Variant
    fType(0) = 0: fData(0) = "text"
    '左到右窗选,右到左框选
    If pt1(0) < pt2(0) Then
        SSet.Select acSelectionSetWindow, pt1, pt2, fType, fData
    Else
        SSet.Select acSelectionSetCrossing, pt1, pt2, fType, fData
    End If
    '遍历选择集并加入字典
    
    Dim objEntity As AcadEntity
    For Each objEntity In SSet
        dic(objEntity.TextString) = dic(objEntity.TextString) + 1
    Next
    
    
End Sub

'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
Public Sub cltj()
    UserForm1.show
End Sub
