Attribute VB_Name = "UserForm1"
Attribute VB_Base = "0{8958D716-F1DE-44A4-BDD9-E1016A4E16AB}{9CC36788-7420-4C42-85B1-1A47B1ECAA72}"
Attribute VB_GlobalNameSpace = False
Attribute VB_Creatable = False
Attribute VB_PredeclaredId = True
Attribute VB_Exposed = False
Attribute VB_TemplateDerived = False
Attribute VB_Customizable = False
Option Explicit



Private Sub CmbBoxbs_Change()
    WriteArrToTxt
End Sub

Private Sub CmbBoxgg_Change()
On Error Resume Next
    Call changeLabel
    SSet.Delete
    deleteArr
    
    clearTextBox
    CmdOK.Enabled = False
    CmdSortMeter.Enabled = False
End Sub

Private Sub CmbBoxwl_Change()
On Error Resume Next
    SSet.Delete
    deleteArr
    
    clearTextBox
    CmdOK.Enabled = False
    CmdSortMeter.Enabled = False
End Sub

Private Sub CmdCancel_Click()
On Error Resume Next
    SSet.Delete
    deleteArr
    End
End Sub

Private Sub CmdOK_Click()
    changeText
    SSet.Delete
    deleteArr
    MsgBox "修改完成"
    clearTextBox
    CmdOK.Enabled = False
    CmdSortMeter.Enabled = False
    
End Sub

Private Sub CmdPick_Click()
    UserForm1.Hide
    If StrComp(CmbBoxwl.text, "2G", vbTextCompare) = 0 Then
        If StrComp(CmbBoxgg.text, "1/2", vbTextCompare) = 0 Then
            ratio = 0.07
        ElseIf StrComp(CmbBoxgg.text, "7/8", vbTextCompare) = 0 Then
            ratio = 0.04
        End If
    ElseIf StrComp(CmbBoxwl.text, "DCS", vbTextCompare) = 0 Then
        If StrComp(CmbBoxgg.text, "1/2", vbTextCompare) = 0 Then
            ratio = 0.105
        ElseIf StrComp(CmbBoxgg.text, "7/8", vbTextCompare) = 0 Then
            ratio = 0.056
        End If
    ElseIf StrComp(CmbBoxwl.text, "3G", vbTextCompare) = 0 Then
        If StrComp(CmbBoxgg.text, "1/2", vbTextCompare) = 0 Then
            ratio = 0.111
        ElseIf StrComp(CmbBoxgg.text, "7/8", vbTextCompare) = 0 Then
            ratio = 0.064
        End If
    ElseIf StrComp(CmbBoxwl.text, "4G", vbTextCompare) = 0 Then
         If StrComp(CmbBoxgg.text, "1/2", vbTextCompare) = 0 Then
            ratio = 0.116
        ElseIf StrComp(CmbBoxgg.text, "7/8", vbTextCompare) = 0 Then
            ratio = 0.068
        End If
    End If
    AddTextToSSet
    AddDatatoArr CmbBoxwl.text, CmbBoxgg.text
    sortArrByGenshu
    WriteArrToTxt
    CmdOK.Enabled = True
    CmdSortMeter.Enabled = True
    UserForm1.show
    
End Sub
'将数组的内容写入文本框控件
Public Sub WriteArrToTxt()
On Error Resume Next
    'Txt11.text = arr(1, 1): Txt12.text = arr(1, 2): Txt13.text = arr(1, 3): Txt14.text = arr(1, 4): Txt15.text = arr(1, 5)
    Dim txtControl As Control
    Dim str As String
    Dim row As Integer
    Dim column As Integer

    For Each txtControl In UserForm1.Controls
        If TypeOf txtControl Is TextBox Then
               
            str = txtControl.Name
            str = Replace(str, "txt", "", , , vbTextCompare)
            If IsNumeric(str) = True Then
                column = Mid(str, Len(str), 1)
                row = Mid(str, 1, Len(str) - 1)
                If row <= UBound(arr) Then
                    txtControl.text = arr(row, column)
                End If
            End If
        End If
    Next txtControl
    
    
    TxtZhonglei.text = UBound(arr)
    Dim sumKxy As Double
    Dim sumKxx As Double
    Dim sumJt As Integer
    sumKxy = 0
    sumKxx = 0
    sumJt = 0
    
    Dim i As Integer
    For i = 1 To UBound(arr)
        sumJt = sumJt + arr(i, 1) '馈线根数总和
        sumKxy = sumKxy + arr(i, 1) * arr(i, 3)
        sumKxx = sumKxx + arr(i, 1) * arr(i, 4)
    Next i
    Txtkxy.text = sumKxy * CmbBoxbs.text
    Txtkxx.text = sumKxx * CmbBoxbs.text
    Txtjt.text = sumJt * 2 * CmbBoxbs.text
End Sub
'清空文本框
Public Sub clearTextBox()
    Dim objControl As Control
    For Each objControl In UserForm1.Controls
        If TypeOf objControl Is TextBox Then
            objControl.text = ""
        End If
        
    Next objControl
End Sub

Private Sub CmdSortMeter_Click()
    If CmdSortMeter.Caption = "按原有米数排序" Then
        sortArrByMishu
        WriteArrToTxt
        CmdSortMeter.Caption = "按馈线根数排序"
    ElseIf CmdSortMeter.Caption = "按馈线根数排序" Then
        sortArrByGenshu
        WriteArrToTxt
        CmdSortMeter.Caption = "按原有米数排序"
    End If
End Sub

Private Sub Label1_Click()

End Sub

Private Sub Txt14_Change()
On Error Resume Next
    changeArr 1, Txt14.text
     WriteArrToTxt
End Sub
Private Sub Txt24_Change()
On Error Resume Next
    changeArr 2, Txt24.text
     WriteArrToTxt
End Sub
Private Sub Txt34_Change()
On Error Resume Next
    changeArr 3, Txt34.text
     WriteArrToTxt
End Sub
Private Sub Txt44_Change()
On Error Resume Next
    changeArr 4, Txt44.text
     WriteArrToTxt
End Sub
Private Sub Txt54_Change()
On Error Resume Next
    changeArr 5, Txt54.text
     WriteArrToTxt
End Sub
Private Sub Txt64_Change()
On Error Resume Next
    changeArr 6, Txt64.text
     WriteArrToTxt
End Sub
Private Sub Txt74_Change()
On Error Resume Next
    changeArr 7, Txt74.text
     WriteArrToTxt
End Sub
Private Sub Txt84_Change()
On Error Resume Next
    changeArr 8, Txt84.text
     WriteArrToTxt
End Sub
Private Sub Txt94_Change()
On Error Resume Next
    changeArr 9, Txt94.text
     WriteArrToTxt
End Sub
Private Sub Txt104_Change()
On Error Resume Next
    changeArr 10, Txt104.text
     WriteArrToTxt
End Sub
Private Sub Txt114_Change()
On Error Resume Next
    changeArr 11, Txt114.text
     WriteArrToTxt
End Sub
Private Sub Txt124_Change()
On Error Resume Next
    changeArr 12, Txt124.text
     WriteArrToTxt
End Sub
Private Sub Txt134_Change()
On Error Resume Next
    changeArr 13, Txt134.text
     WriteArrToTxt
End Sub
Private Sub Txt144_Change()
On Error Resume Next
    changeArr 14, Txt144.text
     WriteArrToTxt
End Sub
Private Sub Txt154_Change()
On Error Resume Next
    changeArr 15, Txt154.text
     WriteArrToTxt
End Sub
Private Sub Txt164_Change()
On Error Resume Next
    changeArr 16, Txt164.text
     WriteArrToTxt
End Sub
Private Sub Txt174_Change()
On Error Resume Next
    changeArr 17, Txt174.text
     WriteArrToTxt
End Sub
Private Sub Txt184_Change()
On Error Resume Next
    changeArr 18, Txt184.text
     WriteArrToTxt
End Sub
Private Sub Txt194_Change()
On Error Resume Next
    changeArr 19, Txt194.text
     WriteArrToTxt
End Sub
Private Sub Txt204_Change()
On Error Resume Next
    changeArr 20, Txt204.text
     WriteArrToTxt
End Sub
Private Sub Txt214_Change()
On Error Resume Next
    changeArr 21, Txt214.text
     WriteArrToTxt
End Sub
Private Sub Txt224_Change()
On Error Resume Next
    changeArr 22, Txt224.text
     WriteArrToTxt
End Sub
Private Sub Txt234_Change()
On Error Resume Next
    changeArr 23, Txt234.text
     WriteArrToTxt
End Sub
Private Sub Txt244_Change()
On Error Resume Next
    changeArr 24, Txt244.text
     WriteArrToTxt
End Sub
Private Sub Txt254_Change()
On Error Resume Next
    changeArr 25, Txt254.text
     WriteArrToTxt
End Sub
Private Sub Txt264_Change()
On Error Resume Next
    changeArr 26, Txt264.text
     WriteArrToTxt
End Sub
Private Sub Txt274_Change()
On Error Resume Next
    changeArr 27, Txt274.text
     WriteArrToTxt
End Sub
Private Sub Txt284_Change()
On Error Resume Next
    changeArr 28, Txt284.text
     WriteArrToTxt
End Sub
Private Sub Txt294_Change()
On Error Resume Next
    changeArr 29, Txt294.text
     WriteArrToTxt
End Sub
Private Sub Txt304_Change()
On Error Resume Next
    changeArr 30, Txt304.text
     WriteArrToTxt
End Sub
Private Sub UserForm_Initialize()

    CmbBoxwl.AddItem "2G"
    CmbBoxwl.AddItem "DCS"
    CmbBoxwl.AddItem "3G"
    CmbBoxwl.AddItem "4G"
    CmbBoxwl.text = "2G"
    CmbBoxgg.AddItem "1/2"
    CmbBoxgg.AddItem "7/8"
    CmbBoxgg.text = "1/2"
    CmbBoxbs.AddItem "1"
    CmbBoxbs.AddItem "2"
    CmbBoxbs.text = "1"
    Call changeLabel
    CmdOK.Enabled = False
    CmdSortMeter.Enabled = False
End Sub
Private Sub changeLabel()
    If StrComp(CmbBoxgg.text, "1/2", vbTextCompare) = 0 Then
        Lblkxy.Caption = "1/2馈线原有:"
        Lblkxx.Caption = "1/2馈线修改后:"
        Lbljt.Caption = "1/2馈线接头:"
        LblZhonglei.Caption = "1/2馈线种类:"
    ElseIf StrComp(CmbBoxgg.text, "7/8", vbTextCompare) = 0 Then
        Lblkxy.Caption = "7/8馈线原有:"
        Lblkxx.Caption = "7/8馈线修改后:"
        Lbljt.Caption = "7/8馈线接头:"
        LblZhonglei.Caption = "7/8馈线种类:"
    End If
End Sub

Attribute VB_Name = "模块1"
Option Explicit
Public SSet As AcadSelectionSet
Public arr() As Variant
Public ratio As Double

'将选取区域的全部文字放入选择集
Public Sub AddTextToSSet()
    Set SSet = createSSet("mySelectSet")
    Dim pt1 As Variant
    Dim pt2 As Variant
    
    pt1 = ThisDrawing.Utility.GetPoint(, "选择对象:")
    pt2 = ThisDrawing.Utility.GetCorner(pt1, "选择对象:")
    Dim fType(0) As Integer
    Dim fData(0) As Variant
    fType(0) = 0: fData(0) = "TEXT"
   
    If pt1(0) < pt2(0) Then
        SSet.Select acSelectionSetWindow, pt1, pt2, fType, fData
    Else
        SSet.Select acSelectionSetCrossing, pt1, pt2, fType, fData
    End If
   
    
End Sub
'拆分字符串到数组
Public Function AddDatatoArr(ByVal wl As String, ByVal gg As String)
    Dim dic As New Dictionary
    Set dic = CreateObject("scripting.dictionary")
    
    Dim min As Double
    Dim max As Double
    If StrComp(wl, "2G", vbTextCompare) = 0 Then
        If StrComp(gg, "1/2", vbTextCompare) = 0 Then
            min = 0.05
            max = 0.12
        ElseIf StrComp(gg, "7/8", vbTextCompare) = 0 Then
            min = 0.02
            max = 0.05
        End If
    Else
         If StrComp(gg, "1/2", vbTextCompare) = 0 Then
            min = 0.09
            max = 0.13
        ElseIf StrComp(gg, "7/8", vbTextCompare) = 0 Then
            min = 0.04
            max = 0.08
        End If
    End If
    AddTextToDic dic, min, max
    
    ReDim arr(1 To dic.Count, 1 To 5) As Variant
    Dim str As String
    Dim first As Integer
    Dim second As Integer
    Dim i As Integer
    For i = 1 To dic.Count
       
        str = dic.Keys(i - 1)
        arr(i, 1) = dic.Item(str)
        arr(i, 2) = str
        
        first = InStr(1, str, "dB/", vbTextCompare)
        second = InStr(1, str, "m", vbTextCompare)
        arr(i, 3) = CDbl(Mid(str, first + 3, second - first - 3))
        arr(i, 4) = arr(i, 3)
        str = CInt(arr(i, 4) * ratio * 10 + 0.01) / 10 & "dB/" & arr(i, 4) & "m"
        str = zhengStr(str)
        arr(i, 5) = str
    Next i
    'Stop
End Function
'字符串整理
Public Function zhengStr(ByVal str As String) As String
     If InStr(1, str, ".", vbTextCompare) = 0 Then
        zhengStr = Replace(str, "dB/", ".0dB/")
     ElseIf InStr(1, str, ".", vbTextCompare) = 1 Then
        zhengStr = "0" & str
     Else
        zhengStr = str
     End If
End Function
'将需要的字符串放入字典
Public Function AddTextToDic(ByVal dic As Dictionary, ByVal min As Double, ByVal max As Double)
    Dim objText As AcadText
    
    Dim firstNum As Double
    Dim secondNum As Double
    Dim first As Integer
    Dim second As Integer
    For Each objText In SSet
        If InStr(1, objText.TextString, "dB/", vbTextCompare) > 0 Then
            first = InStr(1, objText.TextString, "dB/", vbTextCompare)
            second = InStr(1, objText.TextString, "m", vbTextCompare)
            firstNum = Mid(objText.TextString, 1, first - 1)
            secondNum = Mid(objText.TextString, first + 3, second - first - 3)
            If firstNum / secondNum >= min And firstNum / secondNum < max Then
                dic(objText.TextString) = dic(objText.TextString) + 1
            End If
        End If
        
    Next objText
End Function

Public Sub demo()
    Dim test As String
    test = "txt132"
    test = Replace(test, "txt", "")
    MsgBox Mid(test, 1, Len(test) - 1)
End Sub
'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
'修改数组
Public Function changeArr(ByVal row As Integer, ByVal num As Integer)
    arr(row, 4) = num
    
    Dim str As String
    
    str = CInt(arr(row, 4) * ratio * 10 + 0.01) / 10 & "dB/" & arr(row, 4) & "m"
    str = zhengStr(str)
    arr(row, 5) = str
End Function
'修改文字
Public Sub changeText()
    Dim objText As AcadText
    Dim i As Integer
    For Each objText In SSet
        If InStr(1, objText.TextString, "dB/", vbTextCompare) > 0 Then
            For i = 1 To UBound(arr)
                If StrComp(objText.TextString, arr(i, 2), vbTextCompare) = 0 Then
                    objText.TextString = arr(i, 5)
                    Exit For
                End If
            Next i
        End If
    Next objText
End Sub
'删除数组
Public Sub deleteArr()
    Dim i As Integer
    Dim j As Integer
    For i = 1 To UBound(arr)
        For j = 1 To 5
            arr(i, j) = Null
        Next j
    Next i
End Sub
'数组排序
Public Sub sortArrByGenshu()
    Dim i As Integer
    Dim j As Integer
    Dim temp1 As Variant
    Dim temp2 As Variant
    Dim temp3 As Variant
    Dim temp4 As Variant
    Dim temp5 As Variant
    
    For i = 1 To UBound(arr) - 1
        For j = i + 1 To UBound(arr)
            If arr(i, 1) < arr(j, 1) Then
               temp1 = arr(i, 1): arr(i, 1) = arr(j, 1): arr(j, 1) = temp1
               temp2 = arr(i, 2): arr(i, 2) = arr(j, 2): arr(j, 2) = temp2
               temp3 = arr(i, 3): arr(i, 3) = arr(j, 3): arr(j, 3) = temp3
               temp4 = arr(i, 4): arr(i, 4) = arr(j, 4): arr(j, 4) = temp4
               temp5 = arr(i, 5): arr(i, 5) = arr(j, 5): arr(j, 5) = temp5
            End If
        Next j
    Next i
End Sub
Public Sub sortArrByMishu()
    Dim i As Integer
    Dim j As Integer
    Dim temp1 As Variant
    Dim temp2 As Variant
    Dim temp3 As Variant
    Dim temp4 As Variant
    Dim temp5 As Variant
    For i = 1 To UBound(arr) - 1
        For j = i + 1 To UBound(arr)
            If arr(i, 3) > arr(j, 3) Then
               temp1 = arr(i, 1): arr(i, 1) = arr(j, 1): arr(j, 1) = temp1
               temp2 = arr(i, 2): arr(i, 2) = arr(j, 2): arr(j, 2) = temp2
               temp3 = arr(i, 3): arr(i, 3) = arr(j, 3): arr(j, 3) = temp3
               temp4 = arr(i, 4): arr(i, 4) = arr(j, 4): arr(j, 4) = temp4
               temp5 = arr(i, 5): arr(i, 5) = arr(j, 5): arr(j, 5) = temp5
            End If
        Next j
    Next i
End Sub
Public Sub kxxg()
    UserForm1.show
End Sub
