Attribute VB_Name = "Form1"
Attribute VB_Base = "0{4F3AFAE9-8E2C-400D-95C1-B0F308F442C4}{9FB94A0B-A4F0-4272-B4AA-B75B3C82BA68}"
Attribute VB_GlobalNameSpace = False
Attribute VB_Creatable = False
Attribute VB_PredeclaredId = True
Attribute VB_Exposed = False
Attribute VB_TemplateDerived = False
Attribute VB_Customizable = False

Private Sub CmdCancel_Click()
On Error Resume Next
    SSet.Delete
    End
End Sub

Private Sub CmdOK_Click()
On Error Resume Next
    If OptAll.Value = True Then
        AddSSetAll
    End If
    If OptFW.Value = True Then
        If SSet.Count = 0 Then
            Call CmdSelect_Click
        End If
    End If
    
    Call change(TxtFind1.Text, TxtReplace1.Text, TxtFind2.Text, TxtReplace2.Text, TxtFind3.Text, TxtReplace3.Text, TxtFind4.Text, TxtReplace4.Text)
    SSet.Delete
    End
End Sub

Private Sub CmdSelect_Click()
    Form1.Hide
    Call AddSSetFw
    Form1.show
End Sub

Private Sub cmdtxt1_Click()
On Error Resume Next
    Form1.Hide
    Dim objText As AcadText
    Dim pt As Variant
    ThisDrawing.Utility.GetEntity objText, pt, "选择文字:"
    TxtFind1.Text = objText.TextString
    Form1.show
End Sub
Private Sub cmdtxt4_Click()
On Error Resume Next
    Form1.Hide
    Dim objText As AcadText
    Dim pt As Variant
    ThisDrawing.Utility.GetEntity objText, pt, "选择文字:"
    TxtFind4.Text = objText.TextString
    Form1.show
End Sub
Private Sub cmdtxt2_Click()
On Error Resume Next
    Form1.Hide
    Dim objText As AcadText
    Dim pt As Variant
    ThisDrawing.Utility.GetEntity objText, pt, "选择文字:"
    TxtFind2.Text = objText.TextString
    Form1.show
End Sub
Private Sub cmdtxt3_Click()
On Error Resume Next
    Form1.Hide
    Dim objText As AcadText
    Dim pt As Variant
    ThisDrawing.Utility.GetEntity objText, pt, "选择文字:"
    TxtFind3.Text = objText.TextString
    Form1.show
End Sub
Private Sub OptAll_Click()
    CmdSelect.Visible = False
End Sub

Private Sub OptFW_Click()
    If CmdSelect.Visible = False Then
         CmdSelect.Visible = True
    End If
End Sub

Private Sub UserForm_Initialize()
    OptFW.Value = True
    Set SSet = createSSet("mySelectionSet")
End Sub

Attribute VB_Name = "模块1"
Option Explicit

Public SSet As AcadSelectionSet

'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
'按范围选择
Public Sub AddSSetFw()
    Dim fType(0) As Integer
    Dim fData(0) As Variant
    fType(0) = 0: fData(0) = "TEXT"
    SSet.SelectOnScreen fType, fData
End Sub
'全部选择
Public Sub AddSSetAll()
    Dim fType(0) As Integer
    Dim fData(0) As Variant
    fType(0) = 0: fData(0) = "TEXT"
    SSet.Select acSelectionSetAll, , , fType, fData
    
End Sub
'执行替换
Public Sub change(ByVal find1 As String, ByVal replace1 As String, ByVal find2 As String, ByVal replace2 As String, ByVal find3 As String, ByVal replace3 As String, ByVal find4 As String, ByVal replace4 As String)
    Dim objText As AcadText
    Dim i As Integer
    For i = 0 To SSet.Count - 1
        Set objText = SSet.Item(i)
        If StrComp(objText.TextString, find1, vbTextCompare) = 0 Then
            objText.TextString = replace1
        ElseIf StrComp(objText.TextString, find2, vbTextCompare) = 0 Then
            objText.TextString = replace2
        ElseIf StrComp(objText.TextString, find3, vbTextCompare) = 0 Then
            objText.TextString = replace3
        ElseIf StrComp(objText.TextString, find4, vbTextCompare) = 0 Then
            objText.TextString = replace4
        End If
    Next i
End Sub
