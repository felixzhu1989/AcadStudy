Attribute VB_Name = "模块1"
Option Explicit

'实现文字对齐
Public Sub DemoSSetSort()
On Error Resume Next
    Dim objEntity(0) As AcadEntity '选择集的additems方法的参数为数组
    Dim SSet As AcadSelectionSet
    Dim pickedPoint As Variant
    Set SSet = createSSet("mySelectionSet")
'加入误操作判断
xunhuan:    Do
        ThisDrawing.Utility.GetEntity objEntity(0), pickedPoint, "选择对象:"
        If Err <> 0 Then      '通过错误判断退出循坏
            '误操作具体判断语句
            Dim CheckStr As String
            CheckStr = ThisDrawing.Utility.GetString(False, "继续选择请输入<C>,结束选择请输入空格：")
            If StrComp(CheckStr, "c") = 0 Or StrComp(CheckStr, "C") = 0 Then
                Err = 0
                GoTo xunhuan
            Else
                Exit Do
            End If
        End If
        '对图元误选择处理
        If StrComp(objEntity(0).EntityName, "AcDbText", vbTextCompare) = 0 Then
          SSet.AddItems objEntity
       End If
     Loop While IsEmpty(objEntity) = False
    
End Sub

'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
