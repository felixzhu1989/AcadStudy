Attribute VB_Name = "模块1"
Option Explicit
'统计图元个数
Public Sub tongJi()
    Dim SSet As AcadSelectionSet
    Set SSet = createSSet("mySelcetionSet")
    SSet.SelectOnScreen
    
    Dim dic As New Dictionary
    Set dic = CreateObject("scripting.dictionary")
    
    Dim objEntity As AcadEntity
    For Each objEntity In SSet
         dic(objEntity.EntityName) = dic(objEntity.EntityName) + 1
        
'        If dic.Exists(objEntity.EntityName) = False Then
'            dic.Add objEntity.EntityName, 1
'        Else
'            dic.Item(objEntity.EntityName) = dic.Item(objEntity.EntityName) + 1
'        End If
    Next
    
    '提取统计数据
    Dim str As String
    str = ""
    Dim i As Integer
    For i = 0 To dic.Count - 1
        
        str = str & "图元类型:" & dic.Keys(i) & "   个数:" & dic.Item(dic.Keys(i)) & Chr(13)
       ' MsgBox str
    Next i
    MsgBox str
    
End Sub


'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
