Attribute VB_Name = "模块1"
Option Explicit
Public Sub demoDic1()

    Dim dic As New Dictionary
    Set dic = CreateObject("scripting.dictionary")
    dic.Add "A", 10
    dic.Add "B", 20
    dic.Add "C", 30
    dic.Add "D", 10
    'dic.aad "A", 60
    'MsgBox dic.Item("A")
    '提取key值
'    Dim i As Integer
'    For i = 0 To dic.Count - 1
'        MsgBox dic.Keys(i)
'    Next i
     '提取Item值
'     Dim i As Integer
'     For i = 0 To dic.Count - 1
'        MsgBox dic.Items(i)
'     Next i
    '提取key值和对应的item值
'    Dim i As Integer
'    Dim keyStr As String
'    For i = 0 To dic.Count - 1
'        keyStr = dic.Keys(i)
'        keyStr = keyStr & "  " & dic.Item(keyStr)
'        MsgBox keyStr
'    Next i
'    dic.Item("A") = dic.Item("A") + 1
'    MsgBox dic.Item("A")
'
  ' MsgBox dic.Exists("d")
End Sub
Public Sub demoDic2()
    Dim dic As New Dictionary
    Set dic = CreateObject("scripting.dictionary")
    dic.CompareMode = TextCompare
    dic("A") = 10
    dic("B") = 20
    dic("a") = 60
     '提取key值和对应的item值
    Dim i As Integer
    Dim keyStr As String
    For i = 0 To dic.Count - 1
        keyStr = dic.Keys(i)
        keyStr = keyStr & "  " & dic.Item(keyStr)
        MsgBox keyStr
    Next i
    'MsgBox dic("C")
End Sub
Public Sub demoString()
    Dim str1 As String
    Dim str2 As String
    str1 = "12ABcdEF"
    str2 = "12abcDef"
    If StrComp(str1, str2, vbTextCompare) = 0 Then
        MsgBox "true"
    Else
        MsgBox "False"
    End If
End Sub
