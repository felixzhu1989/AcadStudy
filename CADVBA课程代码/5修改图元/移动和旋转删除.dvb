Attribute VB_Name = "模块1"
Option Explicit
'移动图元
Public Sub moveEntity()
    Dim objEntity As AcadEntity
    Dim pt As Variant
    
    ThisDrawing.Utility.GetEntity objEntity, pt, "选择要移动的图元:"
'    Dim fromPoint(2) As Double
'    Dim toPoint(2) As Double
'    fromPoint(0) = 0: fromPoint(1) = 0: fromPoint(2) = 0
'    toPoint(0) = 100: toPoint(1) = 0: toPoint(2) = 0:
'    objEntity.Move fromPoint, toPoint
    Dim fromPoint As Variant
    Dim toPoint As Variant
    fromPoint = ThisDrawing.Utility.GetPoint(, "选择起点:")
    toPoint = ThisDrawing.Utility.GetPoint(fromPoint, "选择终点:")
    objEntity.Move fromPoint, toPoint
End Sub
'旋转图元
Public Sub rotateEntity()
    Dim objEntity As AcadEntity
    Dim pt As Variant
    
    ThisDrawing.Utility.GetEntity objEntity, pt, "选择要旋转的图元:"
    
    Dim basePoint As Variant
    Dim rotationAnlge As Double
    
    basePoint = ThisDrawing.Utility.GetPoint(, "选择旋转基点:")
    rotationAnlge = 3.1415926 / 2
    objEntity.Rotate basePoint, rotationAnlge
    
End Sub
'删除图元
Public Sub deleteEntity()
    Dim objEntity As AcadEntity
    Dim pt As Variant
    
    ThisDrawing.Utility.GetEntity objEntity, pt, "选择要删除的图元:"
    objEntity.Delete
End Sub
