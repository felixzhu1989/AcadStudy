Attribute VB_Name = "模块1"
Option Explicit
Public Sub sendCommandToCAD1()
    'ThisDrawing.SendCommand "line" & vbCr & "0,0,0" & vbCr & "100,100,0" & vbCr & vbCr
    Dim commandStr As String
    commandStr = "circle" & vbCr & "100,100,0" & vbCr & "50" & vbCr
    MsgBox commandStr
    ThisDrawing.SendCommand commandStr
End Sub


Public Sub sendCommandToCAD2()
    Dim ptS As Variant
    Dim ptE As Variant
    Dim commandStr As String
    ptS = ThisDrawing.Utility.GetPoint(, "起点:")
    ptE = ThisDrawing.Utility.GetPoint(ptS, "终点:")
    
    commandStr = "line" & vbCr & changeToLispPoint(ptS) & vbCr & changeToLispPoint(ptE) & vbCr & vbCr
    'MsgBox commandStr
    ThisDrawing.SendCommand commandStr
End Sub
'转化坐标为lisp坐标
Public Function changeToLispPoint(ByVal pt As Variant) As String
    changeToLispPoint = pt(0) & "," & pt(1) & "," & pt(2)
End Function
Public Sub shwoEntity()
    Dim objEntity As AcadEntity
    Dim pt As Variant
    ThisDrawing.Utility.GetEntity objEntity, pt, "选择图元:"
    'MsgBox objEntity.Handle
    Dim str As String
'    str = changeToLispEntity(objentity)
    str = changeToLispEntitySel(objEntity, pt)
    ThisDrawing.SendCommand str
    'MsgBox str
   ' MsgBox Chr(34)
  
End Sub
'转换VBA图元对象到lisp图元对象
Public Function changeToLispEntity(ByVal objEntity As AcadEntity) As String
    changeToLispEntity = "(handent " & Chr(34) & objEntity.Handle & Chr(34) & ")"
End Function
'转换VBA图元对象到lisp图元对象带坐标
Public Function changeToLispEntitySel(ByVal objEntity As AcadEntity, ByVal pt As Variant) As String
    changeToLispEntitySel = "(list (handent " & Chr(34) & objEntity.Handle & Chr(34) & ")" & " (list " & pt(0) & " " & pt(1) & " " & pt(2) & "))"
End Function

'VBA打断
Public Sub VBABreak()
    Dim firstPoint As Variant
    Dim secondPoint As Variant
    Dim objEntity As AcadEntity
    
    ThisDrawing.Utility.GetEntity objEntity, firstPoint, "选择要打断的图元:"
    secondPoint = ThisDrawing.Utility.GetPoint(firstPoint, "选择打断第二点:")
    
    Dim commandStr As String
    commandStr = "break" & vbCr
    commandStr = commandStr & changeToLispEntitySel(objEntity, firstPoint) & vbCr
    commandStr = commandStr & changeToLispPoint(secondPoint) & vbCr
    'MsgBox commandStr
    ThisDrawing.SendCommand commandStr
End Sub
