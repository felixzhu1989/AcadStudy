Attribute VB_Name = "模块1"
Option Explicit
Public Const PI As Double = 3.1415926
'创建圆内接五角星
Public Sub demoStar()
    On Error Resume Next
    Dim objCircle As AcadEntity
    Dim ptPicked As Variant
    
   
xunhuan:
    Do
        ThisDrawing.Utility.GetEntity objCircle, ptPicked, "选择圆:"
        If Err <> 0 Then
            Err.Clear
            Dim check As String
            check = ThisDrawing.Utility.GetString(0, "继续请输入C,退出请按任意键:")
            If check = "c" Or check = "C" Then
                GoTo xunhuan
            Else
               
                Exit Sub
            End If
        End If
        If TypeOf objCircle Is AcadCircle Then
            
             AddStar objCircle.Center, objCircle.radius
             
        End If
        
    Loop While IsEmpty(objCircle) = False
End Sub
Public Function AddStar(ByVal ptCen As Variant, ByVal radius As Double)
    Dim ptArr(9) As Double
    Dim angFromX As Double
    Dim angDiv As Double
    
    Dim objStar As AcadLWPolyline
    angFromX = PI / 2
    angDiv = 2 * PI / 5
    Dim i As Integer
   
    For i = 0 To UBound(ptArr) - 1 Step 2
        
        ptArr(i) = radius * Cos(angFromX + angDiv * i) + ptCen(0)
        ptArr(i + 1) = radius * Sin(angFromX + angDiv * i) + ptCen(1)
    Next
    Set objStar = ThisDrawing.ModelSpace.AddLightWeightPolyline(ptArr)
    objStar.Closed = True
    trimStar objStar, ptArr
End Function
'修剪五角星
Public Function trimStar(ByVal objEntity As AcadEntity, ByRef ptArr() As Double)
    Dim commandStr As String
    commandStr = "trim" & vbCr & vbCr
    'commandStr = commandStr & changeToLispEntity(objEntity) & vbCr
    
    Dim i As Integer
    For i = 0 To UBound(ptArr) Step 2
        commandStr = commandStr & midPoint(ptArr(i), ptArr(i + 1), ptArr((i + 2) Mod 10), ptArr((i + 3) Mod 10)) & vbCr
    Next i
    commandStr = commandStr & vbCr
   ' MsgBox commandStr
  
    ThisDrawing.SendCommand commandStr
     
End Function
'两个点的中点坐标转化为字符串
Public Function midPoint(ByVal x1 As Double, ByVal y1 As Double, ByVal x2 As Double, ByVal y2 As Double) As String
    midPoint = (x1 + x2) / 2 & "," & (y1 + y2) / 2 & "," & "0"
End Function
'转化坐标为lisp坐标
Public Function changeToLispPoint(ByVal pt As Variant) As String
    changeToLispPoint = pt(0) & "," & pt(1) & "," & pt(2)
End Function
'转换VBA图元对象到lisp图元对象
Public Function changeToLispEntity(ByVal objEntity As AcadEntity) As String
    changeToLispEntity = "(handent " & Chr(34) & objEntity.Handle & Chr(34) & ")" & vbCr
End Function
'图元延伸
Public Sub VBAExtend()
    Dim objEntity As AcadEntity
    Dim pt As Variant
    ThisDrawing.Utility.GetEntity objEntity, pt, "选择:"
    
    Dim commandStr As String
    commandStr = "extend" & vbCr & vbCr
    commandStr = commandStr & changeToLispPoint(pt) & vbCr & vbCr
    ThisDrawing.SendCommand commandStr
End Sub
