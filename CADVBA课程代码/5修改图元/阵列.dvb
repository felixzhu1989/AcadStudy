Attribute VB_Name = "模块1"
Option Explicit

'矩形阵列
Public Sub arrayRec()
    Dim objEntity As AcadEntity
    Dim pt As Variant
    ThisDrawing.Utility.GetEntity objEntity, pt, "选择要阵列的图元:"
    Dim rows As Integer
    Dim columns As Integer
    Dim distRows As Double
    Dim distColumns As Double
    rows = 10
    columns = 10
    distRows = -200
    distColumns = -200
    objEntity.ArrayRectangular rows, columns, 1, distRows, distColumns, 0
End Sub
'环形阵列
Public Sub arrayPolar()
    Dim objEntity As AcadEntity
    Dim pt As Variant
    ThisDrawing.Utility.GetEntity objEntity, pt, "选择要阵列的图元:"
    Dim ptC As Variant
    ptC = ThisDrawing.Utility.GetPoint(, "选取阵列中心点:")
    Dim nums As Integer
    nums = 10
    Dim fillAngle As Double
    fillAngle = -3.1415926
    objEntity.arrayPolar nums, fillAngle, ptC
   
End Sub
