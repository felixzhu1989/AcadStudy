Attribute VB_Name = "模块1"
Option Explicit

'复制图元
Public Sub copyEntity()
    Dim objEntity As AcadEntity
    Dim pt As Variant
    Dim copyEntity As AcadEntity
    
    ThisDrawing.Utility.GetEntity objEntity, pt, "选择:"
    Set copyEntity = objEntity.Copy()
    Dim pt1(2) As Double
    Dim pt2(2) As Double
    pt1(0) = 0: pt1(1) = 0: pt1(2) = 0
    pt2(0) = 500: pt2(1) = 0: pt2(2) = 0
    copyEntity.Move pt1, pt2
End Sub
'镜像图元
Public Sub mirrorEntity()
    Dim objEntity As AcadEntity
    Dim pt As Variant
   
    ThisDrawing.Utility.GetEntity objEntity, pt, "选择:"
    Dim pt1 As Variant
    Dim pt2 As Variant
    pt1 = ThisDrawing.Utility.GetPoint(, "第一点:")
    pt2 = ThisDrawing.Utility.GetPoint(pt1, "第二点:")
    objEntity.Mirror pt1, pt2
    objEntity.Delete
    
End Sub
'图元缩放
Public Sub scaleEntity()
     Dim objEntity As AcadEntity
    Dim pt As Variant
   
    ThisDrawing.Utility.GetEntity objEntity, pt, "选择:"
    
    Dim ptBase As Variant
    ptBase = ThisDrawing.Utility.GetPoint(, "选择基点:")
    objEntity.scaleEntity ptBase, 2
End Sub
