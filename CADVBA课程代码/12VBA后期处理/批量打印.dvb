Attribute VB_Name = "frmPlot"
Attribute VB_Base = "0{1C0CD344-2402-4739-B9B0-FDF5FAF01587}{96C375AB-7887-48D0-8A20-85ADA63AC125}"
Attribute VB_GlobalNameSpace = False
Attribute VB_Creatable = False
Attribute VB_PredeclaredId = True
Attribute VB_Exposed = False
Attribute VB_TemplateDerived = False
Attribute VB_Customizable = False
Option Explicit
'设置改变控件的状态
'Private Sub chboxScaleToPaper_Click()
'    If chboxScaleToPaper.Value = False Then
'        cmbboxScaleSel.Enabled = True
'        cmbboxScaleSel.Text = "1:1"
'    Else
'        cmbboxScaleSel.Text = ""
'        cmbboxScaleSel.Enabled = False
'    End If
'End Sub
Private Sub chboxScaleToPaper_Change()
     If chboxScaleToPaper.Value = False Then
        cmbboxScaleSel.Enabled = True
        cmbboxScaleSel.Text = "1:1"
    Else
        cmbboxScaleSel.Text = ""
        cmbboxScaleSel.Enabled = False
    End If
End Sub



Private Sub cmbboxNum_Change()

End Sub

Private Sub cmbboxPlotDeviceName_Change()
    Call addPaperSize
End Sub
'决定是否显示选择范围按钮
Private Sub cmbboxPlotRegion_Change()
    If cmbboxPlotRegion.Text = "全部布局" Then
        cmdPickRegion.Visible = False
    ElseIf cmbboxPlotRegion.Text = "选择范围" Then
        cmdPickRegion.Visible = True
    End If
    SSetOfRegion.Clear
End Sub

Private Sub cmdCancel_Click()
   Unload Me
   'End
End Sub

'单击控件从模型空间选择图元的图层
Private Sub cmdPickLayer_Click()
    Dim objEntity As AcadEntity
    Dim pt
    frmPlot.Hide
    ThisDrawing.Utility.GetEntity objEntity, pt
    cmbboxPlotLayer.Text = objEntity.Layer
    frmPlot.show
End Sub

Private Sub cmdPickRegion_Click()
    frmPlot.Hide
     Call addRegionToSSet(cmbboxPlotLayer.Text, cmbboxPlotRegion.Text)
     frmPlot.show
End Sub

'执行打印操作
Private Sub cmdPlot_Click()
    frmPlot.Hide
    Call batchPlot
    SSetOfRegion.Clear
    frmPlot.show
End Sub

'单击后在模型空间显示
Private Sub cmdShowRegion_Click()
    frmPlot.Hide
    Call showPlotRegion
    frmPlot.show
End Sub



Private Sub SpinButton1_SpinDown()
    txtNum.Text = txtNum.Text - 1
End Sub

Private Sub SpinButton1_SpinUp()
    txtNum.Text = txtNum.Text + 1
End Sub

Private Sub txtNum_Change()
    If IsNumeric(txtNum.Text) = False Then
        MsgBox "请输入数字"
        txtNum.Text = 1
        
    End If
    If IsNumeric(txtNum.Text) = True And txtNum.Text < 1 Then
        txtNum.Text = 1
    End If
    If InStr(1, CStr(txtNum.Text), ".", vbTextCompare) > 0 Then
        MsgBox "打印分数不能为小数"
        txtNum.Text = 1
    End If
End Sub

Private Sub UserForm_Click()

End Sub
'添加打印机到复合框cmbboxPlotDeviceName
Public Function addPlotDeviceNames()
    Dim objLayout As AcadLayout
    Set objLayout = ThisDrawing.ActiveLayout
    Dim plotDeviceNames As Variant
    plotDeviceNames = objLayout.GetPlotDeviceNames
    Dim i As Integer
    For i = 0 To UBound(plotDeviceNames)
        If InStr(1, plotDeviceNames(i), "pc3", vbTextCompare) = 0 Then
            cmbboxPlotDeviceName.AddItem plotDeviceNames(i)
        End If
    Next i
    cmbboxPlotDeviceName.Text = ThisDrawing.ActiveLayout.ConfigName
End Function
'添加图纸尺寸
Public Function addPaperSize()
    Dim paperSize As Variant
    Dim mediaNames As Variant
    ThisDrawing.ActiveLayout.ConfigName = cmbboxPlotDeviceName.Text
    mediaNames = ThisDrawing.ActiveLayout.GetCanonicalMediaNames
    cmbboxPaperSize.Clear
    Dim i As Integer
    For i = 0 To UBound(mediaNames)
        paperSize = ThisDrawing.ActiveLayout.GetLocaleMediaName(mediaNames(i))
        cmbboxPaperSize.AddItem paperSize
    Next
    cmbboxPaperSize.Text = ThisDrawing.ActiveLayout.CanonicalMediaName
End Function
'添加图层信息
Public Function addLayers()
    Dim objLayer As AcadLayer
    For Each objLayer In ThisDrawing.Layers
        cmbboxPlotLayer.AddItem objLayer.Name
        If objLayer.Plottable = False Then
            cmbboxPlotLayer.Text = objLayer.Name
        End If
    Next objLayer
End Function
'设置打印比例
Public Function addPlotScale()
    chboxScaleToPaper.Value = True
    cmbboxScaleSel.AddItem "1:1"
    cmbboxScaleSel.AddItem "1:2"
    cmbboxScaleSel.AddItem "1:4"
    cmbboxScaleSel.AddItem "1:8"
    cmbboxScaleSel.AddItem "1:10"
    cmbboxScaleSel.AddItem "1:16"
    cmbboxScaleSel.AddItem "1:20"
    cmbboxScaleSel.AddItem "1:30"
    cmbboxScaleSel.AddItem "1:40"
    cmbboxScaleSel.AddItem "1:100"
    cmbboxScaleSel.AddItem "2:1"
    cmbboxScaleSel.AddItem "4:1"
    cmbboxScaleSel.AddItem "8:1"
    cmbboxScaleSel.AddItem "10:1"
    cmbboxScaleSel.AddItem "100:1"
'    If chboxScaleToPaper.Value = False Then
'        cmbboxScaleSel.Text = "1:1"
'    Else
'        cmbboxScaleSel.Text = ""
'        cmbboxScaleSel.Enabled = False
'    End If
End Function
'添加打印范围
Public Function addPlotRegion()
    cmbboxPlotRegion.AddItem "全部布局"
    cmbboxPlotRegion.AddItem "选择范围"
    cmbboxPlotRegion.Text = "全部布局"
End Function
'显示选择范围
Public Function showPlotRegion()
    '判断打印范围为"全部布局"或是"选择范围"
    '判断公共变量SSetOfRegion是否空
    If SSetOfRegion.Count = 0 And StrComp(cmbboxPlotRegion.Text, "全部布局", vbTextCompare) = 0 Then
        Call addRegionToSSet(cmbboxPlotLayer.Text, cmbboxPlotRegion.Text)
    ElseIf SSetOfRegion.Count = 0 And StrComp(cmbboxPlotRegion.Text, "选择范围", vbTextCompare) = 0 Then
        MsgBox "请选择打印范围"
        Exit Function
    End If
    '创建临时的选择集用户保存显示范围的图元
    Dim SSetOfShow As AcadSelectionSet
    Set SSetOfShow = createSSet("mySSetShow")
    '声明显示用的坐标点,并取得选择集最小包围点的坐标
    Dim ptMin() As Variant, ptMax() As Variant
    ReDim ptMin(SSetOfRegion.Count - 1) As Variant
    ReDim ptMax(SSetOfRegion.Count - 1) As Variant
    Call addPointToArr(ptMin, ptMax)
    '数组排序
    If OptionButton1.Value = True Then
       Call sortPointArrYX(ptMin, ptMax)
    ElseIf OptionButton2.Value = True Then
       Call sortPointArrXY(ptMin, ptMax)
    End If
    '下面的代码在模型空间的每个图纸上打叉
    Dim objEntity(0) As AcadEntity
    Dim pt1 As Variant
    Dim pt2 As Variant
    Dim pt3(2) As Double
    Dim pt4(2) As Double
    Dim ptCen(2) As Double
    Dim i As Integer
    
    For i = 0 To UBound(ptMin)
        pt1 = ptMin(i): pt2 = ptMax(i)
        pt3(0) = pt1(0): pt3(1) = pt2(1): pt3(2) = 0
        pt4(0) = pt2(0): pt4(1) = pt1(1): pt4(2) = 0
        ptCen(0) = (pt1(0) + pt2(0)) / 2: ptCen(1) = (pt1(1) + pt2(1)) / 2: ptCen(2) = (pt1(2) + pt2(2)) / 2
        Set objEntity(0) = ThisDrawing.ModelSpace.AddLine(pt1, pt2)
        objEntity(0).color = acRed
        SSetOfShow.AddItems objEntity
        Set objEntity(0) = ThisDrawing.ModelSpace.AddLine(pt3, pt4)
        objEntity(0).color = acRed
        SSetOfShow.AddItems objEntity
        Set objEntity(0) = ThisDrawing.ModelSpace.AddText(CStr(i + 1), ptCen, SSetOfShow.Item(SSetOfShow.Count - 1).Length / 5)
        objEntity(0).color = acRed
        SSetOfShow.AddItems objEntity
    Next i
    ThisDrawing.Utility.GetString False, "按空格键返回:"
    SSetOfShow.Erase
    
End Function
'添加打印样式
Public Function addPlotStyle()
    Dim styleNames As Variant
    styleNames = ThisDrawing.ActiveLayout.GetPlotStyleTableNames
    Dim i As Integer
    For i = 0 To UBound(styleNames)
        If InStr(1, styleNames(i), "ctb", vbTextCompare) > 0 Then
            cmbboxStyle.AddItem styleNames(i)
        End If
    Next
    cmbboxStyle.Text = ThisDrawing.ActiveLayout.StyleSheet
End Function
'批量打印函数
Public Function setPlot()
    '设置打印机
    ThisDrawing.ActiveLayout.ConfigName = cmbboxPlotDeviceName.Text
    '设置打印类型
    ThisDrawing.ActiveLayout.PlotType = acWindow
    '设置居中打印
    ThisDrawing.ActiveLayout.CenterPlot = True
    '设置打印样式
    ThisDrawing.ActiveLayout.PlotWithPlotStyles = True
    ThisDrawing.ActiveLayout.ShowPlotStyles = True
    ThisDrawing.ActiveLayout.StyleSheet = cmbboxStyle.Text
    '设置图纸尺寸
    ThisDrawing.ActiveLayout.CanonicalMediaName = cmbboxPaperSize.Text
    '设置打印比例
    If chboxScaleToPaper.Value = True Then
        ThisDrawing.ActiveLayout.StandardScale = acScaleToFit
    Else
        If cmbboxScaleSel.Text = "1:1" Then
            ThisDrawing.ActiveLayout.StandardScale = ac1_1
        ElseIf cmbboxScaleSel.Text = "1:2" Then
            ThisDrawing.ActiveLayout.StandardScale = ac1_2
        ElseIf cmbboxScaleSel.Text = "1:4" Then
            ThisDrawing.ActiveLayout.StandardScale = ac1_4
        ElseIf cmbboxScaleSel.Text = "1:8" Then
            ThisDrawing.ActiveLayout.StandardScale = ac1_8
        ElseIf cmbboxScaleSel.Text = "1:10" Then
            ThisDrawing.ActiveLayout.StandardScale = ac1_10
        ElseIf cmbboxScaleSel.Text = "1:16" Then
            ThisDrawing.ActiveLayout.StandardScale = ac1_16
        ElseIf cmbboxScaleSel.Text = "1:20" Then
            ThisDrawing.ActiveLayout.StandardScale = ac1_20
        ElseIf cmbboxScaleSel.Text = "1:30" Then
            ThisDrawing.ActiveLayout.StandardScale = ac1_30
        ElseIf cmbboxScaleSel.Text = "1:40" Then
            ThisDrawing.ActiveLayout.StandardScale = ac1_40
        ElseIf cmbboxScaleSel.Text = "1:50" Then
            ThisDrawing.ActiveLayout.StandardScale = ac1_50
        ElseIf cmbboxScaleSel.Text = "1:100" Then
            ThisDrawing.ActiveLayout.StandardScale = ac1_100
        ElseIf cmbboxScaleSel.Text = "2:1" Then
            ThisDrawing.ActiveLayout.StandardScale = ac2_1
        ElseIf cmbboxScaleSel.Text = "4:1" Then
            ThisDrawing.ActiveLayout.StandardScale = ac4_1
        ElseIf cmbboxScaleSel.Text = "8:1" Then
            ThisDrawing.ActiveLayout.StandardScale = ac8_1
        ElseIf cmbboxScaleSel.Text = "10:2" Then
            ThisDrawing.ActiveLayout.StandardScale = ac10_1
        ElseIf cmbboxScaleSel.Text = "100:1" Then
            ThisDrawing.ActiveLayout.StandardScale = ac100_1
        
        End If
    End If
    '设置后台打印
    ThisDrawing.SetVariable "BACKGROUNDPLOT", 0
            
End Function
Public Function batchPlot()
   
    '判断打印范围为"全部布局"或是"选择范围"
    '判断公共变量SSetOfRegion是否空
    If SSetOfRegion.Count = 0 And StrComp(cmbboxPlotRegion.Text, "全部布局", vbTextCompare) = 0 Then
        Call addRegionToSSet(cmbboxPlotLayer.Text, cmbboxPlotRegion.Text)
    ElseIf SSetOfRegion.Count = 0 And StrComp(cmbboxPlotRegion.Text, "选择范围", vbTextCompare) = 0 Then
        MsgBox "请选择打印范围"
        Exit Function
    End If
    '声明显示用的坐标点,并取得选择集最小包围点的坐标
    Dim ptMin() As Variant, ptMax() As Variant
    ReDim ptMin(SSetOfRegion.Count - 1) As Variant
    ReDim ptMax(SSetOfRegion.Count - 1) As Variant
    Call addPointToArr(ptMin, ptMax)
    '数组排序
    If OptionButton1.Value = True Then
       Call sortPointArrYX(ptMin, ptMax)
    ElseIf OptionButton2.Value = True Then
       Call sortPointArrXY(ptMin, ptMax)
    End If
    '下面的代码用来实现打印
    Dim objPlot As AcadPlot
    Set objPlot = ThisDrawing.Plot
    Dim ptLB As Variant
    Dim ptRT As Variant
    Dim i As Integer
    Dim numPlot As Integer
    Dim numPaper As Integer
    Dim controlPlot As Integer
    Dim controlPaper As Integer
    '控制逐页还是逐份打印
    If OptionButton3.Value = True Then
        numPlot = txtNum.Text
        numPaper = 1
    ElseIf OptionButton4.Value = True Then
        numPlot = 1
        numPaper = txtNum.Text
    End If
    For controlPlot = 1 To numPlot
        For i = 0 To UBound(ptMin)
            ptLB = ptMin(i): ptRT = ptMax(i)
            ReDim Preserve ptLB(1) As Double
            ReDim Preserve ptRT(1) As Double
            ThisDrawing.ActiveLayout.SetWindowToPlot ptLB, ptRT
            '设置打印范围的方向
            Dim angle2P As Double
            angle2P = ThisDrawing.Utility.AngleFromXAxis(ptMin(i), ptMax(i)) * 180 / 3.1415926
            If angle2P < 45 Then
                ThisDrawing.ActiveLayout.PlotRotation = ac90degrees
            Else
                ThisDrawing.ActiveLayout.PlotRotation = ac0degrees
            End If
            For controlPaper = 1 To numPaper
                objPlot.PlotToDevice
            Next controlPaper
        Next i
    Next controlPlot
End Function
Private Sub UserForm_Initialize()
    Set SSetOfRegion = createSSet("myPlotRegion")
    ThisDrawing.ActiveLayout = ThisDrawing.Layouts.Item("model")
    Call addPlotDeviceNames
    Call addPaperSize
    Call addLayers
    Call addPlotScale
    Call addPlotRegion
    Call addPlotStyle
    txtNum.Text = 1
    OptionButton1.Value = True '默认先行后列
    OptionButton3.Value = True '默认逐份打印
End Sub

Attribute VB_Name = "模块1"
Option Explicit

Public Sub demo()
'    Dim objLayout As AcadLayout
'    For Each objLayout In ThisDrawing.Layouts
'        MsgBox objLayout.Name
'    Next
'    ThisDrawing.ActiveLayout = ThisDrawing.Layouts.Item("model")
    Dim pt1 As Variant
    Dim pt2 As Variant
    pt1 = ThisDrawing.Utility.GetPoint(, "选择打印区域")
    pt2 = ThisDrawing.Utility.GetCorner(pt1, "选择打印区域")
    ReDim Preserve pt1(1) As Double
    ReDim Preserve pt2(1) As Double
    ThisDrawing.ActiveLayout.StandardScale = acScaleToFit
    ThisDrawing.ActiveLayout.PlotRotation = ac0degrees
    ThisDrawing.ActiveLayout.CenterPlot = True
    ThisDrawing.ActiveLayout.CanonicalMediaName = "A3"
    ThisDrawing.SetVariable "BACKGROUNDPLOT", 0
    ThisDrawing.ActiveLayout.SetWindowToPlot pt1, pt2
    
    Dim objPlot As AcadPlot
    Set objPlot = ThisDrawing.Plot
    objPlot.PlotToDevice
End Sub
Public Sub demo1()
    MsgBox ThisDrawing.ActiveLayout.PlotType
End Sub
Public Sub batchPlotRegion()
    '确保当前的布局为模型空间
    ThisDrawing.ActiveLayout = ThisDrawing.Layouts.Item("model")
    '设置打印机或打印到文件
    'ThisDrawing.ActiveLayout.ConfigName = "pdfFactory Pro"
    ThisDrawing.ActiveLayout.ConfigName = "DWG TO PDF.pc3"
    '设置打印类型为窗口
    ThisDrawing.ActiveLayout.PlotType = acWindow
    '设置居中打印
    ThisDrawing.ActiveLayout.CenterPlot = True
    '设置打印比例为布满图纸
    ThisDrawing.ActiveLayout.StandardScale = acScaleToFit
    '设置图纸尺寸
    'ThisDrawing.ActiveLayout.CanonicalMediaName = "A3"
    '设置前台
    ThisDrawing.SetVariable "BACKGROUNDPLOT", 0
    
    Dim objPlot As AcadPlot
    Set objPlot = ThisDrawing.Plot
    
    Dim SSet As AcadSelectionSet
    Set SSet = createSSet("mysel")
    Dim fType(0) As Integer
    Dim fData(0) As Variant
    fType(0) = 8: fData(0) = "plot"
    SSet.Select acSelectionSetAll, , , fType, fData
    Dim objEntity As AcadEntity
    Dim pt1 As Variant
    Dim pt2 As Variant
    Dim i As Integer
    i = 1
    For Each objEntity In SSet
        objEntity.GetBoundingBox pt1, pt2
        ReDim Preserve pt1(1) As Double
        ReDim Preserve pt2(1) As Double
        '设置打印窗口的位置
        ThisDrawing.ActiveLayout.SetWindowToPlot pt1, pt2
        '打印指定区域
        'objPlot.PlotToDevice
        objPlot.PlotToFile "d:\test\" & ThisDrawing.Name & "-" & i & ".pdf"
        i = i + 1
    Next
    
End Sub
'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.add(SSetName)
End Function
Public Sub bp()
    frmPlot.show
End Sub

Attribute VB_Name = "模块2"
Option Explicit
'用于保存打印范围的公共变量
Public SSetOfRegion As AcadSelectionSet
'添加打印范围到选择集SSetOfRegion
Public Function addRegionToSSet(ByVal layerName As String, ByVal region As String)
    SSetOfRegion.Clear
    Dim fType(0) As Integer
    Dim fData(0) As Variant
    fType(0) = 8: fData(0) = layerName
    If StrComp(region, "全部布局", vbTextCompare) = 0 Then
        SSetOfRegion.Select acSelectionSetAll, , , fType, fData
    ElseIf StrComp(region, "选择范围", vbTextCompare) = 0 Then
        SSetOfRegion.SelectOnScreen fType, fData
    End If

End Function
'添加坐标点到数组
Public Function addPointToArr(ByRef ptMin() As Variant, ByRef ptMax() As Variant)
    Dim objEntity As AcadEntity
    Dim i As Integer
    For i = 0 To SSetOfRegion.Count - 1
        Set objEntity = SSetOfRegion.Item(i)
        objEntity.GetBoundingBox ptMin(i), ptMax(i)
    Next
End Function
'数组按照先行后列来排序
Public Function sortPointArrYX(ByRef ptMin() As Variant, ByRef ptMax() As Variant)
    Dim i As Integer
    Dim j As Integer
    Dim ptTemp As Variant
    For i = 0 To UBound(ptMin) - 1
        For j = i + 1 To UBound(ptMin)
            If ptMin(i)(1) < ptMin(j)(1) Then
                ptTemp = ptMin(i): ptMin(i) = ptMin(j): ptMin(j) = ptTemp
                ptTemp = ptMax(i): ptMax(i) = ptMax(j): ptMax(j) = ptTemp
            End If
        Next j
    Next i
    '二次排序
    Dim h As Double
    
    For i = 0 To UBound(ptMin) - 1
        For j = i + 1 To UBound(ptMin)
            h = (ptMax(i)(1) - ptMin(i)(1)) / 3
            If ptMin(i)(1) > ptMin(j)(1) - h And ptMin(i)(1) < ptMin(j)(1) + h And ptMin(i)(0) > ptMin(j)(0) Then
                ptTemp = ptMin(i): ptMin(i) = ptMin(j): ptMin(j) = ptTemp
                ptTemp = ptMax(i): ptMax(i) = ptMax(j): ptMax(j) = ptTemp
            End If
        Next j
    Next i
End Function

'数组按照先列后行来排序
Public Function sortPointArrXY(ByRef ptMin() As Variant, ByRef ptMax() As Variant)
    Dim i As Integer
    Dim j As Integer
    Dim ptTemp As Variant
    For i = 0 To UBound(ptMin) - 1
        For j = i + 1 To UBound(ptMin)
            If ptMin(i)(0) > ptMin(j)(0) Then
                ptTemp = ptMin(i): ptMin(i) = ptMin(j): ptMin(j) = ptTemp
                ptTemp = ptMax(i): ptMax(i) = ptMax(j): ptMax(j) = ptTemp
            End If
        Next j
    Next i
    '二次排序
     Dim w As Double
    For i = 0 To UBound(ptMin) - 1
        For j = i + 1 To UBound(ptMin)
            w = (ptMax(i)(0) - ptMin(i)(0)) / 3
            If ptMin(i)(0) > ptMin(j)(0) - w And ptMin(i)(0) < ptMin(j)(0) + w And ptMin(i)(1) < ptMin(j)(1) Then
                ptTemp = ptMin(i): ptMin(i) = ptMin(j): ptMin(j) = ptTemp
                ptTemp = ptMax(i): ptMax(i) = ptMax(j): ptMax(j) = ptTemp
            End If
        Next j
    Next i
End Function
