Attribute VB_Name = "模块1"
Option Explicit

'新建图层
Public Sub newLayer()
    Dim objLayer As AcadLayer
    Set objLayer = ThisDrawing.Layers.Add("中心线")
End Sub
'删除图层
Public Sub deleteLayer(ByVal layerName As String)
    Dim objLayer As AcadLayer
    Dim i As Integer
    For i = 0 To ThisDrawing.Layers.Count - 1
        Set objLayer = ThisDrawing.Layers.Item(i)
        If StrComp(objLayer.Name, layerName) = 0 Then
    
            objLayer.Delete
        End If
    Next i
End Sub
'图层更名
Public Function renameLayer(ByVal layerName As String, ByVal newName As String)
     Dim objLayer As AcadLayer
    Dim i As Integer
    For i = 0 To ThisDrawing.Layers.Count - 1
        Set objLayer = ThisDrawing.Layers.Item(i)
        If StrComp(objLayer.Name, layerName) = 0 Then
    
            objLayer.Name = newName
            
        End If
    Next i
End Function
Public Sub demo()
    deleteLayer "文字" '0图层不能被删除,也不能更名
    'renameLayer "中心线", "文字"
    'TCshezhi "文字"
End Sub

'图层相关属性的设置
Public Function TCshezhi(ByVal layerName As String)
     Dim objLayer As AcadLayer
    Dim i As Integer
    For i = 0 To ThisDrawing.Layers.Count - 1
        Set objLayer = ThisDrawing.Layers.Item(i)
        If StrComp(objLayer.Name, layerName) = 0 Then
'            objLayer.LayerOn = False
'            objLayer.Freeze = True
'            objLayer.Lock = True
'            Dim color As New AcadAcCmColor
'            color.ColorIndex = 12
'            objLayer.TrueColor = color
            objLayer.color = 35
            objLayer.Lineweight = acLnWt050
            
            'ThisDrawing.Linetypes.Load "dashdot2", "acad.lin"
            
            objLayer.Linetype = "dashdot2"
            ThisDrawing.ActiveLayer = objLayer
        End If
    Next i
End Function
'批量删除空白图层
Public Sub deleteBlankLayer()
    Dim objLayer As AcadLayer
    Set objLayer = ThisDrawing.Layers.Item(0)
    ' MsgBox objLayer.Name
    '设置0图层为当前图层
    ThisDrawing.ActiveLayer = objLayer
    '将图层先放入图层数组
    Dim objLayerArr() As AcadLayer
    ReDim objLayerArr(ThisDrawing.Layers.Count - 2) As AcadLayer
    Dim i As Integer
    For i = 1 To ThisDrawing.Layers.Count - 1
        Set objLayerArr(i - 1) = ThisDrawing.Layers.Item(i)
    Next i
    
    Dim SSet As AcadSelectionSet
    Dim fType(0) As Integer
    Dim fData(0) As Variant
    fType(0) = 8
    Set SSet = createSSet("my")
    
    For i = 0 To UBound(objLayerArr)
        Set objLayer = objLayerArr(i)
        fData(0) = objLayer.Name
        SSet.Select acSelectionSetAll, , , fType, fData
        If SSet.Count = 0 Then
            objLayer.Delete
        End If
        SSet.Clear
    Next i
End Sub
'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
