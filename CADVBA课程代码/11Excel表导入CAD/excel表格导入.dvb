Attribute VB_Name = "UserForm1"
Attribute VB_Base = "0{3DC2AEE2-FDE7-4599-845F-BBBD20A8BA81}{2A87BE18-DC5A-4ADD-9BF5-0D31375DE7C1}"
Attribute VB_GlobalNameSpace = False
Attribute VB_Creatable = False
Attribute VB_PredeclaredId = True
Attribute VB_Exposed = False
Attribute VB_TemplateDerived = False
Attribute VB_Customizable = False
Option Explicit


Private Sub cmdCancel_Click()
    Unload Me
End Sub

Private Sub cmdOK_Click()
On Error Resume Next
    '获取插入点坐标
    Dim ptInsert(2) As Double
    ptInsert(0) = txtX.Text: ptInsert(1) = txtY.Text: ptInsert(2) = 0
    '获取并连接当前但开的excel程序及当前表
    Dim excelApp As Object
    Dim excelSheet As Object
    Set excelApp = GetObject(, "excel.application")
    If Err <> 0 Then
        MsgBox "Excel程序未运行,请打开Excel程序!"
        Err.Clear
        Exit Sub
    End If
    
    Set excelSheet = excelApp.activesheet
    '保存要转化的区域
    Dim ranges As Object
    If optAll.Value = True Then
        Set ranges = excelSheet.usedrange
    ElseIf optSelect = True Then
        Set ranges = excelApp.Selection
    End If
    '对每个单元进行操作
    Dim excelRg As Object
    For Each excelRg In ranges
        addTableAndText ranges, excelRg, ptInsert
       
    Next excelRg
   '释放Excel对象
   Set excelSheet = Nothing
   Set excelApp = Nothing
End Sub
'转化表格的函数
Public Function addTableAndText(ByVal ranges As Object, ByVal excelRg As Object, ByVal ptInsert As Variant)
    '声明一个AcadLine对象,以便后续对其处理
    Dim objLine As AcadLine
    '声明四个坐标变量
    Dim ptLT(2) As Double
    Dim ptLB(2) As Double
    Dim ptRT(2) As Double
    Dim ptRB(2) As Double
    '声明一个单元格对象来求顶点坐标
    Dim rg11 As Object
    Set rg11 = excelRg.Offset(1, 1)
    '获取四个顶点的坐标
    ptLT(0) = ptInsert(0) + excelRg.Left * 0.8 - ranges.Left * 0.8
    ptLT(1) = ptInsert(1) - (excelRg.top - ranges.top)
    ptLT(2) = 0
    ptRB(0) = ptInsert(0) + rg11.Left * 0.8 - ranges.Left * 0.8
    ptRB(1) = ptInsert(1) - (rg11.top - ranges.top)
    ptRB(2) = 0
    ptLB(0) = ptLT(0)
    ptLB(1) = ptRB(1)
    ptLB(2) = 0
    ptRT(0) = ptRB(0)
    ptRT(1) = ptLT(1)
    ptRT(2) = 0
    '左侧线
    If excelRg.Column = ranges.Column And excelRg.borders.Item(1).linestyle > 0 Then
         Set objLine = ThisDrawing.ModelSpace.AddLine(ptLT, ptLB)
         setTableColor objLine, excelRg.borders.Item(1).color
    End If
    '右侧线
    If excelRg.borders.Item(2).linestyle > 0 Then
         Set objLine = ThisDrawing.ModelSpace.AddLine(ptRT, ptRB)
         setTableColor objLine, excelRg.borders.Item(2).color
    End If
    '上边线
    If excelRg.row = ranges.row And excelRg.borders.Item(3).linestyle > 0 Then
         Set objLine = ThisDrawing.ModelSpace.AddLine(ptLT, ptRT)
         setTableColor objLine, excelRg.borders.Item(3).color
    End If
    '下边线
    If excelRg.borders.Item(4).linestyle > 0 Then
         Set objLine = ThisDrawing.ModelSpace.AddLine(ptLB, ptRB)
         setTableColor objLine, excelRg.borders.Item(4).color
    End If
    '添加文字
    Dim objText As AcadText
    Set objText = ThisDrawing.ModelSpace.AddText(excelRg.Text, ptLB, excelRg.Font.Size * 0.9)
    '设置文字的颜色
    setTextColor objText, excelRg.Font.color
    '设置文字的对其方式
    setTextAlignMent objText, ptLT, ptRB
End Function
'改变表格的颜色
Public Function setTableColor(ByVal objEntity As AcadEntity, ByVal color As Long)
    If optTableColor2.Value = True Then
        If cmbTableColor.Text = "By Layer" Then
            Exit Function
        ElseIf cmbTableColor.Text = "红色" Then
            objEntity.color = acRed
        ElseIf cmbTableColor.Text = "绿色" Then
            objEntity.color = acGreen
        ElseIf cmbTableColor.Text = "蓝色" Then
            objEntity.color = acBlue
        End If
        Exit Function
    End If
    Dim colorR As Long
    Dim colorG As Long
    Dim colorB As Long
    
    If optTableColor1.Value = True Then
        If color <> 0 Then
            Dim entityColor As AcadAcCmColor
            Set entityColor = AcadApplication.GetInterfaceObject("AutoCAD.AcCmColor.19")
            colorR = color And 255
            colorG = (color And 65280) / 256
            colorB = (color And 16711680) / 65536
            entityColor.SetRGB colorR, colorG, colorB
            objEntity.TrueColor = entityColor
        End If
    End If
End Function
'改变文字的颜色
Public Function setTextColor(ByVal objEntity As AcadEntity, ByVal color As Long)
    If optTextColor2.Value = True Then
        If cmbTextColor.Text = "By Layer" Then
            Exit Function
        ElseIf cmbTextColor.Text = "红色" Then
            objEntity.color = acRed
        ElseIf cmbTextColor.Text = "绿色" Then
            objEntity.color = acGreen
        ElseIf cmbTextColor.Text = "蓝色" Then
            objEntity.color = acBlue
        End If
        Exit Function
    End If
    Dim colorR As Long
    Dim colorG As Long
    Dim colorB As Long
    
    If optTextColor1.Value = True Then
        If color <> 0 Then
            Dim entityColor As AcadAcCmColor
            Set entityColor = AcadApplication.GetInterfaceObject("AutoCAD.AcCmColor.19")
            colorR = color And 255
            colorG = (color And 65280) / 256
            colorB = (color And 16711680) / 65536
            entityColor.SetRGB colorR, colorG, colorB
            objEntity.TrueColor = entityColor
        End If
    End If
End Function
'文字的对齐
Public Function setTextAlignMent(ByVal objText As AcadText, ByVal ptLT As Variant, ByVal ptRB As Variant)
    Dim ptMC(2) As Double
    ptMC(0) = (ptLT(0) + ptRB(0)) / 2
    ptMC(1) = (ptLT(1) + ptRB(1)) / 2
    ptMC(2) = 0
    If optTextAlignment1.Value = True Then
        objText.Alignment = acAlignmentMiddleCenter
        objText.Move objText.TextAlignmentPoint, ptMC
        Exit Function
    End If
    Dim ptML(2) As Double
    ptML(0) = ptLT(0)
    ptML(1) = (ptLT(1) + ptRB(1)) / 2
    ptML(2) = 0
    If optTextAlignment2.Value = True Then
        objText.Alignment = acAlignmentMiddleLeft
        objText.Move objText.TextAlignmentPoint, ptML
        Exit Function
    End If
    Dim ptMR(2) As Double
    ptMR(0) = ptRB(0)
    ptMR(1) = (ptLT(1) + ptRB(1)) / 2
    ptMR(2) = 0
    If optTextAlignment3.Value = True Then
        objText.Alignment = acAlignmentMiddleRight
        objText.Move objText.TextAlignmentPoint, ptMR
    End If
End Function
Private Sub cmdPickPoint_Click()
On Error Resume Next
    Dim pt As Variant
    UserForm1.Hide
    pt = ThisDrawing.Utility.GetPoint(, "请选择插入点:")
    txtX.Text = pt(0): txtY.Text = pt(1)
    UserForm1.show
End Sub
'设置下拉框的内容
Public Function addCombbox()
    cmbTableColor.AddItem "By Layer"
    cmbTableColor.AddItem "红色"
    cmbTableColor.AddItem "绿色"
    cmbTableColor.AddItem "蓝色"
    cmbTextColor.AddItem "By Layer"
    cmbTextColor.AddItem "红色"
    cmbTextColor.AddItem "绿色"
    cmbTextColor.AddItem "蓝色"
End Function


Private Sub optTableColor1_Change()
    If optTableColor1.Value = True Then
        cmbTableColor.Enabled = False
        cmbTableColor.Text = ""
    End If
End Sub

Private Sub optTableColor2_Click()
    If optTableColor2.Value = True Then
        cmbTableColor.Enabled = True
        cmbTableColor.Text = "By Layer"
    End If
End Sub

Private Sub optTextColor1_Change()
     If optTextColor1.Value = True Then
        cmbTextColor.Enabled = False
        cmbTextColor.Text = ""
     End If
End Sub


Private Sub optTextColor2_Change()
    If optTextColor2.Value = True Then
        cmbTextColor.Enabled = True
        cmbTextColor.Text = "By Layer"
     End If
End Sub



Private Sub UserForm_Initialize()
    txtX.Text = 0: txtY.Text = 0
    optAll.Value = True
    optTableColor1.Value = True
    optTextColor1.Value = True
    addCombbox
    optTextAlignment1.Value = True
End Sub

Attribute VB_Name = "模块1"
Option Explicit
Public Sub demo()
'    Dim objEntity As AcadEntity
'    Dim pt As Variant
'    ThisDrawing.Utility.GetEntity objEntity, pt
'    Stop
    MsgBox ThisDrawing.Application.Version
End Sub
Public Sub excelin()
    UserForm1.show
End Sub
