Attribute VB_Name = "模块1"
Option Explicit

Public Sub showEntity()
    Dim objEntity As AcadEntity
    Dim pt As Variant
    ThisDrawing.Utility.GetEntity objEntity, pt
    Stop
End Sub
'创建块
Public Sub createBlockTX()
    Dim objBlock As AcadBlock
    Dim ptBase(2) As Double '插入块时的基点
    
    Dim pt1(2) As Double
    Dim pt2(2) As Double
    Dim pt3(2) As Double
    Dim pt4(2) As Double
    pt1(0) = 2: pt1(1) = 0: pt1(2) = 0
    pt2(0) = -2: pt2(1) = 0: pt2(2) = 0
    pt3(0) = 0: pt3(1) = 2: pt3(2) = 0
    pt4(0) = 0: pt4(1) = -2: pt4(2) = 0
    
    Dim ptArr(3) As Double
    ptArr(0) = 2: ptArr(1) = 0: ptArr(2) = -2: ptArr(3) = 0
    ptBase(0) = 0: ptBase(1) = 0: ptBase(2) = 0
    
    Set objBlock = ThisDrawing.Blocks.Add(ptBase, "天线")
    objBlock.AddLine pt1, pt2
    objBlock.AddLine pt3, pt4
    objBlock.AddCircle ptBase, 2
    objBlock.AddLightWeightPolyline ptArr
    
    '更改块中多段线的属性
    Dim objLWP As AcadLWPolyline
    Set objLWP = objBlock.Item(3)
    objLWP.SetBulge 0, 1
    objLWP.SetBulge 1, 1
    objLWP.Closed = True
    objLWP.ConstantWidth = 0.5
    
End Sub
Public Sub demo()
    'createBlock "天线1"
'    Dim pt As Variant
'    Dim blockName As String
    
'    pt = ThisDrawing.Utility.GetPoint(, "选择插入点:")
'    blockName = "天线1"
    
'    insertBlock blockName, pt
'    Dim objBlock As AcadBlock
'    Set objBlock = ThisDrawing.Blocks.Item("天线1")
'    objBlock.Delete
    'MsgBox isExistBlock("天线")
    deleteBlock "全向天线"
End Sub
Public Function insertBlock(ByVal blockName As String, ByVal ptInsert As Variant)
    ThisDrawing.ModelSpace.insertBlock ptInsert, blockName, 1, 1, 1, 0
End Function
'选择图元,转化为快
Public Function createBlock(ByVal blockName As String)
    Dim SSet As AcadSelectionSet
    Set SSet = createSSet("myBLock")
    Dim objBlock As AcadBlock
    Dim ptBase As Variant
    Dim objectBlock() As Object
    '拾取块的基点
    ptBase = ThisDrawing.Utility.GetPoint(, "选择块的基点:")
    Set objBlock = ThisDrawing.Blocks.Add(ptBase, blockName)
    
    '选择要加入块的图元
    SSet.SelectOnScreen
    Dim i As Integer
    ReDim objectBlock(SSet.Count - 1)
    For i = 0 To SSet.Count - 1
        Set objectBlock(i) = SSet.Item(i)
    Next i
    SSet.Delete
    
    ThisDrawing.CopyObjects objectBlock, objBlock
End Function
'删除块
Public Function deleteBlock(ByVal blockName As String)
    If isExistBlock(blockName) = False Then
        MsgBox "找不要要删除的块"
        Exit Function
    End If
    '选择块对应的参照
    Dim SSet As AcadSelectionSet
    Set SSet = createSSet("myBlockRef")
    Dim fType(2) As Integer
    Dim fData(2) As Variant
    fType(0) = 0: fData(0) = "insert"
    fType(1) = 100: fData(1) = "AcDbBlockReference"
    fType(2) = 2: fData(2) = blockName
    SSet.Select acSelectionSetAll, , , fType, fData
    
    '删除块对应的参照
    
    If SSet.Count <> 0 Then
        If MsgBox("要删除的块在模型空间里有参照,是否和参照一起删除", vbOKCancel, "块删除提示") = vbCancel Then
            Exit Function
        End If
        
        SSet.Erase
        SSet.Delete
    End If
   
    Dim objBlock As AcadBlock
    Set objBlock = ThisDrawing.Blocks.Item(blockName)
    objBlock.Delete
End Function
'判断图形文件中是否包含指定的块
Public Function isExistBlock(ByVal blockName As String) As Boolean
    Dim objBlock As AcadBlock
    Dim i As Integer
    For i = 0 To ThisDrawing.Blocks.Count - 1
        Set objBlock = ThisDrawing.Blocks.Item(i)
        If StrComp(objBlock.Name, blockName, vbTextCompare) = 0 Then
            isExistBlock = True
            Exit Function
        End If
    Next i
    
    isExistBlock = False
    
End Function
'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
