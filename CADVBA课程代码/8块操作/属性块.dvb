Attribute VB_Name = "模块1"
Option Explicit


'创建块带属性的块
Public Sub createATTBlockTX()
    Dim objBlock As AcadBlock
    Dim ptBase(2) As Double '插入块时的基点
    
    Dim pt1(2) As Double
    Dim pt2(2) As Double
    Dim pt3(2) As Double
    Dim pt4(2) As Double
    pt1(0) = 2: pt1(1) = 0: pt1(2) = 0
    pt2(0) = -2: pt2(1) = 0: pt2(2) = 0
    pt3(0) = 0: pt3(1) = 2: pt3(2) = 0
    pt4(0) = 0: pt4(1) = -2: pt4(2) = 0
    
    Dim ptArr(3) As Double
    ptArr(0) = 2: ptArr(1) = 0: ptArr(2) = -2: ptArr(3) = 0
    ptBase(0) = 0: ptBase(1) = 0: ptBase(2) = 0
    
    Set objBlock = ThisDrawing.Blocks.Add(ptBase, "全向天线")
    objBlock.AddLine pt1, pt2
    objBlock.AddLine pt3, pt4
    objBlock.AddCircle ptBase, 2
    objBlock.AddLightWeightPolyline ptArr
    
    '更改块中多段线的属性
    Dim objLWP As AcadLWPolyline
    Set objLWP = objBlock.Item(3)
    objLWP.SetBulge 0, 1
    objLWP.SetBulge 1, 1
    objLWP.Closed = True
    objLWP.ConstantWidth = 0.5
    
    '设置块的属性
    ptBase(0) = 4: ptBase(1) = 0.5: ptBase(2) = 0
    objBlock.AddAttribute 2, acAttributeModeLockPosition, "ANT1-1F", ptBase, "编号：", "ANT1-1F"
    ptBase(0) = 4: ptBase(1) = -2.5: ptBase(2) = 0
    objBlock.AddAttribute 2, acAttributeModeLockPosition, "10.0dBm", ptBase, "功率：", "10.0dBm"
    
End Sub
'插入属性块
Public Function insertATTBlock(ByVal blockName As String, ByVal pt As Variant) As AcadBlockReference
    Set insertATTBlock = ThisDrawing.ModelSpace.InsertBlock(pt, blockName, 1, 1, 1, 0)
End Function
Public Sub demo()
'     Dim objRef As AcadBlockReference
'     Dim pt As Variant
'     ThisDrawing.Utility.GetEntity objRef, pt, ""
'
'     Dim att As Variant
'     att = objRef.GetAttributes
'     Stop
    Dim objBlockRef As AcadBlockReference
    Dim pt As Variant
    Dim blockName As String
    blockName = "全向天线"
    pt = ThisDrawing.Utility.GetPoint(, "指定插入点：")
    
    Set objBlockRef = insertATTBlock(blockName, pt)
    
    Dim blockATT As Variant
    blockATT = objBlockRef.GetAttributes
    blockATT(0).TextString = "ANT2-2F"
    blockATT(1).TextString = "12.2dBm"
    
End Sub
'批量更改属性块的属性1
Public Sub changeATT()
     '选择块对应的参照
    Dim SSet As AcadSelectionSet
    Set SSet = createSSet("myBlockRef")
    Dim fType(2) As Integer
    Dim fData(2) As Variant
    fType(0) = 0: fData(0) = "insert"
    fType(1) = 100: fData(1) = "AcDbBlockReference"
    fType(2) = 2: fData(2) = "全向天线"
    SSet.SelectOnScreen fType, fData
    
    '更改属性
    Dim objBlockRef As AcadBlockReference
    Dim i As Integer
    Dim blockATT As Variant
    
    For i = 1 To SSet.Count
        Set objBlockRef = SSet.Item(i - 1)
        blockATT = objBlockRef.GetAttributes
        blockATT(0).TextString = "ANT" & i & "-2F"
    Next i
    SSet.Delete
End Sub
'批量更改属性块的属性2
Public Sub changeATTbyOrder()
     '选择块对应的参照
    Dim SSet As AcadSelectionSet
    Set SSet = createSSet("myBlockRef")
    Dim fType(2) As Integer
    Dim fData(2) As Variant
    fType(0) = 0: fData(0) = "insert"
    fType(1) = 100: fData(1) = "AcDbBlockReference"
    fType(2) = 2: fData(2) = "全向天线"
    SSet.SelectOnScreen fType, fData
    
    
    Dim objBlockRef As AcadBlockReference
    Dim objBREFArr() As Variant
    ReDim objBREFArr(0 To (SSet.Count - 1), 0 To 1)
    Dim i As Integer
    i = 0
    For Each objBlockRef In SSet
        Set objBREFArr(i, 0) = objBlockRef
        objBREFArr(i, 1) = objBlockRef.InsertionPoint(1)
        i = i + 1
    Next
    SSet.Delete
    
    '按坐标排序
    sortATT objBREFArr
    Dim blockATT As Variant
    For i = 0 To UBound(objBREFArr)
        Set objBlockRef = objBREFArr(i, 0)
        blockATT = objBlockRef.GetAttributes
        blockATT(0).TextString = "ANT" & (i + 1) & "-2F"
    Next
    
End Sub
'数组排序
Public Function sortATT(ByRef objArr() As Variant)
    Dim i As Integer
    Dim j As Integer
    Dim objRef As AcadBlockReference
    Dim ptY As Double
    For i = 0 To UBound(objArr) - 1
        For j = i + 1 To UBound(objArr)
            If objArr(i, 1) < objArr(j, 1) Then
                Set objRef = objArr(i, 0)
                Set objArr(i, 0) = objArr(j, 0)
                Set objArr(j, 0) = objRef
                ptY = objArr(i, 1)
                objArr(i, 1) = objArr(j, 1)
                objArr(j, 1) = ptY
            End If
        Next j
    Next i
End Function



'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
