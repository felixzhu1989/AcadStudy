Attribute VB_Name = "模块1"
Option Explicit

Public Sub demo()

    ThisDrawing.SelectionSets.Add "mySelectionSet"
   ' MsgBox ThisDrawing.SelectionSets.Count
 
End Sub
'Public Function createSSet(ByVal SSetName As String) As AcadSelectionSet
'On Error Resume Next
'    Dim SSet As AcadSelectionSet
'    Set SSet = ThisDrawing.SelectionSets.Item(SSetName)
'    SSet.Delete
'
'    Set createSSet = ThisDrawing.SelectionSets.Add(SSetName)
'End Function
'安全创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function
Public Sub demoSSet1()
    Dim SSet As AcadSelectionSet
    Set SSet = createSSet("mySelectionSet")
    SSet.Select acSelectionSetAll
    
    Dim objEntity As AcadEntity
'    Dim i As Integer
'    For i = 0 To SSet.Count - 1
'        Set objEntity = SSet.Item(i)
'        objEntity.color = acMagenta
'    Next i
     For Each objEntity In SSet
        objEntity.color = acRed
     Next objEntity
End Sub
Public Sub demoSSet2()
    Dim SSet As AcadSelectionSet
    Set SSet = createSSet("mySelectionSet")
    Dim pt1 As Variant
    Dim pt2 As Variant
    pt1 = ThisDrawing.Utility.GetPoint(, "选择图元:")
    pt2 = ThisDrawing.Utility.GetCorner(pt1, "选择图元:")
    If pt1(0) < pt2(0) Then
        SSet.Select acSelectionSetWindow, pt1, pt2
    Else
        SSet.Select acSelectionSetCrossing, pt1, pt2
    End If
'    SSet.SelectOnScreen
    Dim objEntity As AcadEntity

     For Each objEntity In SSet
        objEntity.color = acRed
     Next objEntity
End Sub
Public Sub demoSSet3()
    Dim SSet As AcadSelectionSet
    Set SSet = createSSet("mySelectionSet")
    Dim pt1 As Variant
    Dim pt2 As Variant
    pt1 = ThisDrawing.Utility.GetPoint(, "选择图元:")
    pt2 = ThisDrawing.Utility.GetCorner(pt1, "选择图元:")
    
    Dim fType(4) As Integer '这里必须是integer
    Dim fData(4) As Variant '这里必须是Variant
    fType(0) = -4: fData(0) = "<or"
    fType(1) = 0: fData(1) = "circle"
    fType(2) = 0: fData(2) = "text"
    fType(3) = -4: fData(3) = "or>"
    fType(4) = 8: fData(4) = "0"
    If pt1(0) < pt2(0) Then
        SSet.Select acSelectionSetWindow, pt1, pt2, fType, fData
    Else
        SSet.Select acSelectionSetCrossing, pt1, pt2, fType, fData
    End If
'    SSet.SelectOnScreen
    Dim objEntity As AcadEntity

     For Each objEntity In SSet
        objEntity.color = acRed
     Next objEntity
End Sub
