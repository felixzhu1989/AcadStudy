Attribute VB_Name = "模块1"
Option Explicit

'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function

Public Sub demoAddSSet()
    Dim SSet As AcadSelectionSet
    Set SSet = createSSet("mySelectionSet")
    SSet.SelectOnScreen
    Stop
End Sub
    
Public Sub demoOutSSet()
On Error Resume Next
    Dim SSet As AcadSelectionSet
    Set SSet = createSSet("mySelectionSet")
    Dim objEntity(0) As AcadEntity
    Dim ptPicked As Variant
    
xunhuan:    Do
        ThisDrawing.Utility.GetEntity objEntity(0), ptPicked, "选择对象:"
        If Err <> 0 Then      '通过错误判断退出循坏
            '误操作具体判断语句
            Dim CheckStr As String
            CheckStr = ThisDrawing.Utility.GetString(False, "继续选择请输入<C>,结束选择请输入空格：")
            If StrComp(CheckStr, "c") = 0 Or StrComp(CheckStr, "C") = 0 Then
                Err.Clear
                GoTo xunhuan
            Else
                Exit Do
            End If
        End If
        '对图元误选择处理
        If StrComp(objEntity(0).EntityName, "AcDbText", vbTextCompare) = 0 Then
          SSet.AddItems objEntity
        End If
    Loop While IsEmpty(objEntity) = False
    Dim i As Integer
    Dim str As String
    Dim objText As AcadText
    For i = 0 To SSet.Count - 1
        Set objText = SSet.Item(i)
        MsgBox objText.TextString
    Next i
   
End Sub
