Attribute VB_Name = "模块1"
Option Explicit
'查看多段线的凸度
Public Sub Lwdemo()
   Dim objEntity As AcadEntity
   Dim pt As Variant
   Dim bulge() As Double
   ThisDrawing.Utility.GetEntity objEntity, pt, "选择多段线:"
   Dim DDS As Integer
   DDS = polylineDDS(objEntity)
   ReDim bugle(0 To (DDS - 1)) As Double
   
   Dim i As Integer
   For i = 0 To DDS - 1
      bugle(i) = objEntity.GetBulge(i)
   Next i
   Stop
End Sub
'获取多段线的顶点数
Public Function polylineDDS(ByVal objEntity As AcadEntity) As Integer
    Dim pt As Variant
    If TypeOf objEntity Is AcadLWPolyline Then
        pt = objEntity.Coordinates
        polylineDDS = (UBound(pt) + 1) / 2
    End If
    
    If TypeOf objEntity Is AcadPolyline Then
        pt = objEntity.Coordinates
        polylineDDS = (UBound(pt) + 1) / 3
    End If
   
End Function

'画圆型的多段线
Public Sub CLWPolyline()
    Dim pt1 As Variant
    Dim pt2 As Variant
   
    Dim ptArr(5) As Double
    
    pt1 = ThisDrawing.Utility.GetPoint(, "1:")
    pt2 = ThisDrawing.Utility.GetPoint(, "2:")
   
    
    ptArr(0) = pt1(0): ptArr(1) = pt1(1)
    ptArr(2) = pt2(0): ptArr(3) = pt2(1)
     ptArr(4) = pt1(0): ptArr(5) = pt1(1)
    Dim objLW As AcadLWPolyline
    Set objLW = ThisDrawing.ModelSpace.AddLightWeightPolyline(ptArr)
    objLW.SetBulge 0, 1
    objLW.SetBulge 1, 1
End Sub

Attribute VB_Name = "模块2"
Option Explicit
'测试宏
Public Sub demo()
    Dim objEntity As AcadEntity
    Dim ptPicked As Variant
    ThisDrawing.Utility.GetEntity objEntity, ptPicked
    
    If TypeOf objEntity Is AcadLine Then
        Dim objLWL As AcadLWPolyline
        Set objLWL = lineToLWPolyline(objEntity)
        objEntity.Delete
    End If
    
    If TypeOf objEntity Is AcadCircle Then
        Dim objLWC As AcadLWPolyline
        Set objLWC = circleToLWPolyline(objEntity)
        objEntity.Delete
    End If
    
    If TypeOf objEntity Is AcadArc Then
        Dim objLWA As AcadLWPolyline
        Set objLWA = ArcToLWPolyline(objEntity)
        objEntity.Delete
    End If
        
End Sub


'直线转化为多段线
Public Function lineToLWPolyline(ByVal objLine As AcadLine) As AcadLWPolyline
    Dim ptArr(3) As Double
    ptArr(0) = objLine.StartPoint(0): ptArr(1) = objLine.StartPoint(1)
    ptArr(2) = objLine.EndPoint(0): ptArr(3) = objLine.EndPoint(1)
    
    Dim objLWPolyline As AcadLWPolyline
    Set objLWPolyline = ThisDrawing.ModelSpace.AddLightWeightPolyline(ptArr)
    objLWPolyline.color = objLine.color
    objLWPolyline.ConstantWidth = objLine.Lineweight
    Set lineToLWPolyline = objLWPolyline
End Function
'园转换为多段线
Public Function circleToLWPolyline(ByVal objCircle As AcadCircle) As AcadLWPolyline
    Dim ptCen As Variant
    Dim ptArr(3) As Double
    
    ptCen = objCircle.Center
    ptArr(0) = objCircle.radius + ptCen(0)
    ptArr(1) = ptCen(1)
    ptArr(2) = ptCen(0) - objCircle.radius
    ptArr(3) = ptCen(1)
'    ptArr(4) = objCircle.radius + ptCen(0)
'    ptArr(5) = ptCen(1)
    
    Dim objLWP As AcadLWPolyline
    Set objLWP = ThisDrawing.ModelSpace.AddLightWeightPolyline(ptArr)
    objLWP.SetBulge 0, 1
    objLWP.SetBulge 1, 1
    objLWP.Closed = True
    Set circleToLWPolyline = objLWP
End Function
'圆弧转换为多段线
Public Function ArcToLWPolyline(ByVal objArc As AcadArc) As AcadLWPolyline
    Dim ptCen As Variant
    Dim ptArr(3) As Double
    ptCen = objArc.Center
    ptArr(0) = ptCen(0) + objArc.radius * Cos(objArc.StartAngle)
    ptArr(1) = ptCen(1) + objArc.radius * Sin(objArc.StartAngle)
    ptArr(2) = ptCen(0) + objArc.radius * Cos(objArc.EndAngle)
    ptArr(3) = ptCen(1) + objArc.radius * Sin(objArc.EndAngle)
    
    Dim objLWP As AcadLWPolyline
    Set objLWP = ThisDrawing.ModelSpace.AddLightWeightPolyline(ptArr)
    If objArc.EndAngle < objArc.StartAngle Then
        objLWP.SetBulge 0, Tan(((objArc.EndAngle + 2 * 3.1415926) - objArc.StartAngle) / 4)
    Else
        objLWP.SetBulge 0, Tan((objArc.EndAngle - objArc.StartAngle) / 4)
    End If
    Set ArcToLWPolyline = objLWP
End Function
