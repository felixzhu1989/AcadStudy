Attribute VB_Name = "模块1"
Option Explicit
Public Sub joinLWPolyline()
    Dim SSet As AcadSelectionSet
    Set SSet = createSSet("myse")
    SSet.SelectOnScreen
    
    Dim commandStr As String
    
    commandStr = "pedit" & vbCr & "m" & vbCr & changeToLispSSet(SSet) & vbCr & "j" & vbCr & vbCr & vbCr
    'MsgBox commandStr
    ThisDrawing.SendCommand commandStr
End Sub

'转换成lisp选择集
Public Function changeToLispSSet(ByVal SSet As AcadSelectionSet) As String
    If SSet.Count = 0 Then
        Exit Function
    End If
    
    Dim i As Integer
    Dim ssetString As String
    For i = 0 To SSet.Count - 1
        ssetString = ssetString & "(handent " & Chr(34) & SSet.Item(i).Handle & Chr(34) & ")" & vbCr
    Next i
    changeToLispSSet = ssetString
End Function
'创建选择集
Public Function createSSet(ByVal SSetName As String) As AcadSelectionSet
    Dim SSet As AcadSelectionSet
    Dim i As Integer
    For i = 0 To ThisDrawing.SelectionSets.Count - 1
        Set SSet = ThisDrawing.SelectionSets.Item(i)
        If StrComp(SSet.Name, SSetName, vbTextCompare) = 0 Then
            SSet.Delete
            Exit For
        End If
    Next i
    Set createSSet = ThisDrawing.SelectionSets.Add(SSetName)
End Function

Public Sub Bound()
    Dim pt As Variant
    pt = ThisDrawing.Utility.GetPoint(, "拾取内部点:")
    
    Dim commandStr As String
    commandStr = "-boundary" & vbCr & changeToLispPoint(pt) & vbCr & vbCr
    ThisDrawing.SendCommand commandStr
    
    Dim objEntity As AcadEntity
    Dim entityCount As Integer
    entityCount = ThisDrawing.ModelSpace.Count
    Set objEntity = ThisDrawing.ModelSpace.Item(entityCount - 1)
    objEntity.color = acCyan
    objEntity.ConstantWidth = 0.5
    
End Sub
Public Function changeToLispPoint(ByVal pt As Variant) As String
    changeToLispPoint = pt(0) & "," & pt(1)
End Function
