Attribute VB_Name = "模块1"
Option Explicit
Public Const PI As Double = 3.1415926
Public Sub demoText()
On Error Resume Next
    Dim objText As AcadEntity
    Dim ptPicked As Variant
    Dim minPt As Variant
    Dim maxPt As Variant
    'Dim objRect As AcadLWPolyline
xunhuan:
    Do
        ThisDrawing.Utility.GetEntity objText, ptPicked, "选择文字:"
        If Err <> 0 Then
            Err.Clear
            Dim check As String
            check = ThisDrawing.Utility.GetString(0, "继续请输入C,退出请按任意键:")
            If check = "c" Or check = "C" Then
                GoTo xunhuan
            Else
               
                Exit Sub
            End If
        End If
        If TypeOf objText Is AcadText Then
            objText.GetBoundingBox minPt, maxPt
'            minPt(0) = minPt(0) - 2: minPt(1) = minPt(1) - 2
'            maxPt(0) = maxPt(0) + 2: maxPt(1) = maxPt(1) + 2
            'Set objRect = AddRect2P(minPt, maxPt)
            'objRect.color = acRed
            AddCircle2P minPt, maxPt
        End If
        
    Loop While IsEmpty(objText) = False
End Sub
'通过多段线创建矩形,并进行封装
Public Function AddRect2P(ByVal pt1 As Variant, ByVal pt2 As Variant) As AcadLWPolyline
   
    Dim ptArr(7) As Double
    Dim objRec As AcadLWPolyline
    
    ptArr(0) = pt1(0): ptArr(1) = pt1(1)
    ptArr(2) = pt2(0): ptArr(3) = pt1(1)
    ptArr(4) = pt2(0): ptArr(5) = pt2(1)
    ptArr(6) = pt1(0): ptArr(7) = pt2(1)
    
    Set objRec = ThisDrawing.ModelSpace.AddLightWeightPolyline(ptArr)
    objRec.Closed = True
    Set AddRect2P = objRec
End Function
'通过两点创建圆,两点为圆的直径上的两个点
Public Function AddCircle2P(ByVal pt1 As Variant, pt2 As Variant) As AcadCircle
    Dim ptCen(2) As Double
    Dim radius As Double
    ptCen(0) = (pt1(0) + pt2(0)) / 2
    ptCen(1) = (pt1(1) + pt2(1)) / 2
    ptCen(2) = (pt1(2) + pt2(2)) / 2
    radius = Sqr((pt1(0) - pt2(0)) ^ 2 + (pt1(1) - pt2(1)) ^ 2) / 2
    Set AddCircle2P = ThisDrawing.ModelSpace.AddCircle(ptCen, radius)
End Function
'创建圆内接五角星
Public Sub demoStar()
    On Error Resume Next
    Dim objCircle As AcadEntity
    Dim ptPicked As Variant
    
   
xunhuan:
    Do
        ThisDrawing.Utility.GetEntity objCircle, ptPicked, "选择圆:"
        If Err <> 0 Then
            Err.Clear
            Dim check As String
            check = ThisDrawing.Utility.GetString(0, "继续请输入C,退出请按任意键:")
            If check = "c" Or check = "C" Then
                GoTo xunhuan
            Else
               
                Exit Sub
            End If
        End If
        If TypeOf objCircle Is AcadCircle Then
            
             AddStar objCircle.Center, objCircle.radius
             
        End If
        
    Loop While IsEmpty(objCircle) = False
End Sub
Public Function AddStar(ByVal ptCen As Variant, ByVal radius As Double) As AcadLWPolyline
    Dim ptArr(9) As Double
    Dim angFromX As Double
    Dim angDiv As Double
    
    Dim objStar As AcadLWPolyline
    angFromX = PI / 2
    angDiv = 2 * PI / 5
    Dim i As Integer
   
    For i = 0 To UBound(ptArr) - 1 Step 2
        
        ptArr(i) = radius * Cos(angFromX + angDiv * i) + ptCen(0)
        ptArr(i + 1) = radius * Sin(angFromX + angDiv * i) + ptCen(1)
    Next
    Set objStar = ThisDrawing.ModelSpace.AddLightWeightPolyline(ptArr)
    objStar.Closed = True
    Set AddStar = objStar
End Function
