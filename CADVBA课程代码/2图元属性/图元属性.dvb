Attribute VB_Name = "模块1"
Option Explicit

Public Sub changeCircle()
On Error Resume Next
    Dim objCircle As AcadEntity
    Dim ptpicked As Variant
    
    ThisDrawing.Utility.GetEntity objCircle, ptpicked, "请选择圆:"
    'If objCircle.EntityName = "AcDbCircle" Then
    If StrComp(objCircle.EntityName, "AcDbCircle", vbTextCompare) = 0 Then
    'objCircle.Radius = objCircle.Radius * 2
    objCircle.color = acGreen
'    Else
'        MsgBox "您选择的不是圆"
    End If

End Sub

Public Sub demo1()
    Dim objEntity As AcadEntity
    Dim ptpicked As Variant
    ThisDrawing.Utility.GetEntity objEntity, ptpicked, "选择图元:"
    MsgBox objEntity.EntityName
    
End Sub
Sub ChkFirstWhile()
    Dim counter As Integer
    Dim myNum As Integer
    counter = 0
    myNum = 20
    Do While myNum > 10
        myNum = myNum - 1
        counter = counter + 1
    Loop
    MsgBox "The loop made " & counter & " repetitions."
End Sub
Sub ChkLastWhile()
    Dim counter As Integer
    Dim myNum As Integer
    counter = 0
    myNum = 9
    Do
        myNum = myNum - 1
        counter = counter + 1
    Loop While myNum > 10
    MsgBox "The loop made " & counter & " repetitions."
End Sub

Sub ChkFirstUntil()
    Dim counter As Integer
    Dim myNum As Integer
    counter = 0
    myNum = 20
    Do Until myNum = 10
        myNum = myNum - 1
        counter = counter + 1
    Loop
    MsgBox "The loop made " & counter & " repetitions."
End Sub
Sub ChkLastUntil()
    Dim counter As Integer
    Dim myNum As Integer
    counter = 0
    myNum = 1
    Do
        myNum = myNum + 1
        counter = counter + 1
    Loop Until myNum = 10
    MsgBox "The loop made " & counter & " repetitions."
End Sub
'更改文字属性
Public Sub changeText1()
On Error Resume Next
    Dim objText As AcadEntity
    Dim pt As Variant
    
    ThisDrawing.Utility.GetEntity objText, pt, "选择文字:"
    
    Dim str As String
    Do While IsEmpty(objText) = False
        If TypeOf objText Is AcadText Then
            str = ThisDrawing.Utility.GetString(True, "新内容:")
            objText.TextString = str
        End If
        ThisDrawing.Utility.GetEntity objText, pt, "选择文字:"
        If Err <> 0 Then
            Err.Clear
            Exit Sub
        End If
    Loop
    
End Sub
