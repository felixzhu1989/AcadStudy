Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit

Private Sub AcadDocument_BeginCommand(ByVal CommandName As String)
    If StrComp(CommandName, "move", vbTextCompare) = 0 Then
        SendKeys "{ESC}" & "{ESC}", True
    ElseIf StrComp(CommandName, "line", vbTextCompare) = 0 Then
        newLayer ("直线")
        ThisDrawing.ActiveLayer = ThisDrawing.Layers.Item("圆")
    ElseIf StrComp(CommandName, "circle", vbTextCompare) = 0 Then
        newLayer ("圆")
        ThisDrawing.ActiveLayer = ThisDrawing.Layers.Item("圆")
    ElseIf StrComp(CommandName, "pline", vbTextCompare) = 0 Then
        newLayer ("多线")
        ThisDrawing.ActiveLayer = ThisDrawing.Layers.Item("多线")
    ElseIf StrComp(CommandName, "arc", vbTextCompare) = 0 Then
        newLayer ("圆弧")
        ThisDrawing.ActiveLayer = ThisDrawing.Layers.Item("圆弧")
    ElseIf StrComp(CommandName, "text", vbTextCompare) = 0 Then
        newLayer ("文字")
        ThisDrawing.ActiveLayer = ThisDrawing.Layers.Item("文字")
    End If
    
End Sub

Attribute VB_Name = "模块1"
Option Explicit

'创建新图层
Public Function newLayer(ByVal layerName As String)
    If isExistLayer(layerName) = False Then
        ThisDrawing.Layers.Add (layerName)
    End If
End Function
'判断指定图层是否存在
Public Function isExistLayer(ByVal layerName) As Boolean
    'Dim objLayer As AcadLayer
    Dim i As Integer
    For i = 1 To ThisDrawing.Layers.Count - 1
        If StrComp(ThisDrawing.Layers.Item(i).Name, layerName, vbTextCompare) = 0 Then
            isExistLayer = True
            Exit Function
        End If
    Next i
    isExistLayer = False
End Function
