Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit

Private Sub AcadDocument_BeginDoubleClick(ByVal PickPoint As Variant)
   Dim SSet As AcadSelectionSet
   Set SSet = ThisDrawing.PickfirstSelectionSet
   
   '判断是否单击时,单击了对象
   If SSet.Count = 0 Then
        Exit Sub
   End If
   
   '我们只选取一个对象
   If TypeOf SSet.Item(0) Is AcadText Then
        Set objText = SSet.Item(0)
        Load frmTxt
        frmTxt.show
   
        SendKeys "{ESC}" & "{ESC}", True
   End If
   
End Sub

Attribute VB_Name = "frmTxt"
Attribute VB_Base = "0{4D4F61EC-0D3C-47DC-A4A1-7B8F9F901AA6}{D1A5C1D5-2615-4914-B80B-E60021D50B2A}"
Attribute VB_GlobalNameSpace = False
Attribute VB_Creatable = False
Attribute VB_PredeclaredId = True
Attribute VB_Exposed = False
Attribute VB_TemplateDerived = False
Attribute VB_Customizable = False
Option Explicit

Private Sub cmdCancel_Click()
    Unload frmTxt
End Sub

Private Sub cmdOK_Click()
    objText.TextString = Txt1.Text
    Unload frmTxt
End Sub



Private Sub UserForm_Initialize()
    Txt1.Text = objText.TextString
End Sub

Attribute VB_Name = "模块1"
Option Explicit

Public objText As AcadText
