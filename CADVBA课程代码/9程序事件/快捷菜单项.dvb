Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit

Private Sub AcadDocument_BeginSave(ByVal FileName As String)

End Sub

Private Sub AcadDocument_BeginShortcutMenuEdit(ShortcutMenu As IAcadPopupMenu, SelectionSet As IAcadSelectionSet)
    On Error Resume Next
    Dim newMenuItem As AcadPopupMenuItem
    Dim itemString As String
    
    itemString = Chr(vbKeyEscape) + Chr(vbKeyEscape) + "-vbarun" + Chr(vbKeySpace) + "thisdrawing.changeColor" + Chr(vbKeySpace)
    Set newMenuItem = ShortcutMenu.AddMenuItem(0, Chr(Asc("&")) + "修改颜色", itemString)
    Set SSet = SelectionSet
End Sub
'更改颜色的宏
Public Sub changeColor()
    Dim objEntity As AcadEntity
    For Each objEntity In SSet
        objEntity.color = acMagenta
    Next
    SSet.Delete
End Sub

Attribute VB_Name = "模块1"
Option Explicit

Public SSet As AcadSelectionSet
